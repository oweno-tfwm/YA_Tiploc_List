FME workspace TiplocCleaner05.fmw

Parameters:
- inputPath =
- outputFile =
- outputPath =

Note: NAPTAN is the best quality data source / -has TIPLOC no STANOX / **some records no TIPLOC / https://beta-naptan.dft.gov.uk/download/national
Creator
    GEOMTYPE = Geometry Object
    NUM = 1
    CREATED -> NaptanTIPLOC [INITIATOR]
NaptanTIPLOC: FeatureReader
    ATTRIBUTES = CSV,"AtcoCode,NaptanCode,CommonName,ShortCommonName,Easting,Northing,Longitude,Latitude,StopType,ModeType,RailType,Tiploc,Crs,StopAreaRef,AdministrativeAreaRef"
    ATTR_ACCUM_MODE = Only Use Result
    COMBINE_GEOM = Use Result
    COORDSYS = LL-WGS84
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = AtcoCode,varchar(16),YES;NaptanCode,varchar(32),YES;CommonName,varchar(64),YES;ShortCommonName,varchar(32),YES;Easting,int64,YES;Northing,int64,YES;Longitude,x_coordinate,YES;Latitude,y_coordinate,YES;StopType,varchar(4),YES;ModeType,varchar(5),YES;RailType,varchar(11),YES;Tiploc,varchar(16),YES;Crs,varchar(4),YES;StopAreaRef,varchar(16),YES;AdministrativeAreaRef,uint32,YES
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(inputPath)\NaptanStopPoints.csv
    FORMAT = CSV2
    INTERACT = NONE
    OUTPUT_FEATURES_DISPLAY = Schema and Data Features
    CSV -> createSource_NAPTAN
    INITIATOR -> ATOC_msn_tiploc [INITIATOR]
createSource_NAPTAN: AttributeCreator
    ATTR_TABLE = SET_TO dataSource = NAPTAN
    -> nullTiploc
nullTiploc: TestFilter
    DEFAULT_VALUE = OK
    TEST_LIST:
      "BOOL_OP,OR,COMPOSITE_TEST,""""""1 OR 2"""""",TEST_CLAUSE,CASE_SENSITIVE_TEST Tiploc ATTRIBUTE_VALUE_NULL ""
      CASE_SENSITIVE_TEST Tiploc NOT_ATTRIBUTE_HAS_A_VALUE """,NULL
    NULL -> AttributeCreator_7
    OK -> AttributeRenamer_3
Note: NAPTAN data includes some non NR stations e.g. Weardale Railway
Note: Where we don't have a TIPLOC use ATCO code instead
AttributeCreator_7
    ATTR_TABLE = SET_TO TIPLOC = @Value(AtcoCode)
    -> AttributeRenamer_2
AttributeRenamer_2
    ATTR_TABLE = RENAME_SET_DEFAULT CommonName > Description
    MISSING_INPUT_ATTRS = REMOVE
    -> testGeometry
AttributeRenamer_3
    ATTR_TABLE:
      RENAME_SET_DEFAULT Tiploc > TIPLOC
      RENAME_SET_DEFAULT Crs > CRS
      RENAME_SET_DEFAULT CommonName > Description
    MISSING_INPUT_ATTRS = REMOVE
    -> testGeometry
testGeometry: TestFilter
    DEFAULT_VALUE = good Geometry
    TEST_LIST:
      "BOOL_OP,OR,COMPOSITE_TEST,""""""1 OR 2"""""",TEST_CLAUSE,TEST Easting ATTRIBUTE_VALUE_NULL ""
      TEST Northing ATTRIBUTE_VALUE_NULL """,NULL Geometry
    NULL Geometry -> joinTiploc [LEFT]
    good Geometry -> joinTiploc_2 [LEFT]
Note: ATOC is 2nd best quality data source / coordinates encoded in strange way / (apart from in Ireland where it's systematically wrong - CRS / projection issue?) / https://data.atoc.org/how-to
Note: 'CRS reference code' is unique - can be multiple for a station e.g. Tamworth low level - high level. / 'CRS code' may repeat (multiple TIPLOCS per CRS)
ATOC_msn_tiploc: FeatureReader
    ATTRIBUTES = CSV,"""Station Name"",""CATE Interchange status"",""TIPLOC Code"",""CRS Reference Code"",""CRS Code"",""Ordnance Survey Grid Ref East"",Estimate,""Ordnance Survey Grid Ref North"",""Minimum Change Time"",Footnote,""Sub-sector code"""
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = Station Name,varchar(31),YES;CATE Interchange status,uint32,YES;TIPLOC Code,varchar(8),YES;CRS Reference Code,varchar(4),YES;CRS Code,varchar(4),YES;Ordnance Survey Grid Ref East,int64,YES;Estimate,varchar(2),YES;Ordnance Survey Grid Ref North,int64,YES;Minimum Change Time,uint32,YES;Footnote,varchar(1),YES;Sub-sector code,varchar(1),YES
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(inputPath)\owen.txt
    FORMAT = CSV2
    INTERACT = NONE
    OUTPUT_FEATURES_DISPLAY = Schema and Data Features
    CSV -> createSource_ATOC
    INITIATOR -> TPS [INITIATOR]
createSource_ATOC: AttributeCreator
    ATTR_TABLE = SET_TO dataSource = ATOC
    -> AttributeCreator
AttributeCreator
    ATTR_TABLE:
      SET_TO Ordnance Survey Grid Ref East = FME_CONDITIONAL:DEFAULT_VALUE'@Evaluate(100*(@Value(Ordnance Survey Grid Ref East)-10000))'BOOL_OP;OR;COMPOSITE_TEST;1;NUM_TEST @Value(Ordnance Survey Grid Ref East) <= 0'FME_NULL_VALUE'FME_NUM_CONDITIONS2___
      SET_TO Ordnance Survey Grid Ref North = FME_CONDITIONAL:DEFAULT_VALUE'@Evaluate(100*(@Value(Ordnance Survey Grid Ref North)-60000))'BOOL_OP;OR;COMPOSITE_TEST;1;NUM_TEST @Value(Ordnance Survey Grid Ref North) <= 0'FME_NULL_VALUE'BOOL_OP;OR;COMPOSITE_TEST;1;NUM_TEST @Value(Ordnance Survey Grid Ref North) >= 69999'FME_NULL_VALUE'FME_NUM_CONDITIONS3___
    -> testIreland
Note: Ireland data is rubbish - use UK2GTFS instead
testIreland: TestFilter
    DEFAULT_VALUE = <UNFILTERED>
    TEST_LIST:
      "BOOL_OP,AND,COMPOSITE_TEST,""""""1 AND 2 AND 3"""""",TEST_CLAUSE,NUM_TEST @Value(Ordnance Survey Grid Ref East) <= 147500
      NUM_TEST @Value(Ordnance Survey Grid Ref North) <= 610000
      NUM_TEST @Value(Ordnance Survey Grid Ref North) >= 260000",Ireland,"BOOL_OP,OR,COMPOSITE_TEST,""""""1 OR 2"""""",TEST_CLAUSE,TEST Ordnance Survey Grid Ref East ATTRIBUTE_VALUE_NULL ""
      TEST Ordnance Survey Grid Ref North ATTRIBUTE_VALUE_NULL """,NULL grid ref
    <UNFILTERED> -> CoordinateSystemSetter_NG_2
CoordinateSystemSetter_NG_2
    COORDSYS = EPSG:27700
    -> VertexCreator_4
VertexCreator_4
    MEASURE_TYPE = Continuous
    MODE_NAME = Replace with Point
    XVAL = @Value(Ordnance Survey Grid Ref East)
    YVAL = @Value(Ordnance Survey Grid Ref North)
    -> AttributeRenamer_4
    <REJECTED> -> AttributeRenamer_4
AttributeRenamer_4
    ATTR_TABLE:
      RENAME_SET_DEFAULT TIPLOC Code > TIPLOC
      RENAME_SET_DEFAULT Station Name > Description
    MISSING_INPUT_ATTRS = REMOVE
    -> reproject-LL_2
reproject-LL_2: Reprojector
    DEST = LL-WGS84
    INTERPOLATION_TYPE_NAME = Nearest Neighbor
    RASTER_CELL_SIZE = Preserve Cells
    RASTER_TOLERANCE = 0.0
    REPROJECTED -> joinTiploc [RIGHT]
Note: Only a tiny number of rows in TPS actually have any geometry / (even those aren't great quality) / https://wiki.openraildata.com/index.php?title=Reference_Data / https://publicdatafeeds.networkrail.co.uk/ntrod/SupportingFileAuthenticate?type=TPS
TPS: FeatureReader
    ATTRIBUTES = CSV,"stationid,uiccode,abbrev,longname,commentary,stdstoppingtime,stdconnectiontime,stationtype,stationcategory,uicstationcode,transportassociation,easting,northing,stanox,lpbflag,periodid,capitalsident,nalco,nlccheckchr,pomcpcode,crscode,desccapri,compulsorystop,hasopeninghours,isparent,lastuse,lastmodified"
    ATTR_ACCUM_MODE = Only Use Result
    COMBINE_GEOM = Use Result
    COORDSYS = EPSG:27700
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = stationid,uint32,YES;uiccode,uint32,YES;abbrev,varchar(8),YES;longname,varchar(27),YES;commentary,varchar(39),YES;stdstoppingtime,uint32,YES;stdconnectiontime,uint32,YES;stationtype,uint32,YES;stationcategory,uint32,YES;uicstationcode,uint32,YES;transportassociation,varchar(1),YES;x,real64,NO;y,real64,NO;easting,x_coordinate,YES;northing,y_coordinate,YES;stanox,uint32,YES;lpbflag,varchar(1),YES;periodid,uint32,YES;capitalsident,uint32,YES;nalco,real64,YES;nlccheckchr,varchar(2),YES;pomcpcode,uint32,YES;crscode,varchar(4),YES;desccapri,varchar(1),YES;compulsorystop,varchar(6),YES;hasopeninghours,uint32,YES;isparent,varchar(5),YES;lastuse,varchar(11),YES;lastmodified,varchar(20),YES
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(inputPath)\tps-locations.csv
    FORMAT = CSV2
    INTERACT = NONE
    OUTPUT_FEATURES_DISPLAY = Schema and Data Features
    CSV -> createSource_TPS
    INITIATOR -> readerWoodpecker [INITIATOR]
createSource_TPS: AttributeCreator
    ATTR_TABLE = SET_TO dataSource = TPS
    -> TestFilter_8
TestFilter_8
    DEFAULT_VALUE = <UNFILTERED>
    TEST_LIST = "BOOL_OP,OR,COMPOSITE_TEST,""""""1"""""",TEST_CLAUSE,CASE_SENSITIVE_TEST @Value(abbrev) IN ABTHA39",Bad
    Bad -> AttributeValueMapper_3
    <UNFILTERED> -> reproject-LL_5
Note: everyone say 'typo' all together
AttributeValueMapper_3
    DEFAULT_VALUE = @Value(northing)
    DIRECTION = Forward (Source To Destination)
    LUT = 766451,166451
    SRC = northing
    VAL_ATTR = northing
    -> VertexCreator_6
VertexCreator_6
    MEASURE_TYPE = Continuous
    MODE_NAME = Replace with Point
    XVAL = @Value(easting)
    YVAL = @Value(northing)
    -> reproject-LL_5
reproject-LL_5: Reprojector
    DEST = LL-WGS84
    INTERPOLATION_TYPE_NAME = Nearest Neighbor
    RASTER_CELL_SIZE = Preserve Cells
    RASTER_TOLERANCE = 0.0
    REPROJECTED -> clipCountry [CLIPPEE]
Note: https://github.com/anisotropi4/woodpecker / licence: Apache License 2.0 / https://github.com/anisotropi4/woodpecker/blob/main/LICENSE
Note: Everything has STANOX- some blank TIPLOC
readerWoodpecker: FeatureReader
    ATTRIBUTES = STANOX,"STANOX,NLC,TIPLOC,3ALPHA,UIC,NLCDESC,NLCDESC16,fid",nx,"STANOX,TIPLOC,ELR,3ALPHA,UIC,NLCDESC,ASSETID,L_SYSTEM,TRID,L_M_FROM,L_M_TO,d,osmid,fid",ox,"STANOX,TIPLOC,name,ELR,3ALPHA,UIC,NLCDESC,osmid,d,fid",segment,"ASSETID,M_POST_ID,offset,L_LINK_ID,L_SYSTEM,ELR,TRID,TRCODE,L_M_FROM,L_M_TO,SHAPE_LEN,osmid,km_from,km_to,source,source_asset,target,target_asset,fid",sx,"STANOX,TIPLOC,ELR,3ALPHA,UIC,NLCDESC,ASSETID,L_SYSTEM,TRID,L_M_FROM,L_M_TO,d,offset,fid"
    ATTR_ACCUM_MODE = Only Use Result
    COMBINE_GEOM = Use Result
    DATASET = $(inputPath)\tiploc-location.gpkg
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    STANOX -> createSource_woodpecker
    INITIATOR -> readerRailmap [INITIATOR]
createSource_woodpecker: AttributeCreator
    ATTR_TABLE:
      SET_TO dataSource = woodpecker
      SET_TO TIPLOC = @Trim(@Value(TIPLOC))
      SET_TO 3ALPHA = @Trim(@Value(3ALPHA))
      SET_TO NLCDESC = @Trim(@Value(NLCDESC))
      SET_TO STANOX = @Evaluate(@int(@Trim(@Value(STANOX))))
      SET_TO STANOXwp = @Value(STANOX)
    -> AttributeRenamer
AttributeRenamer
    ATTR_TABLE:
      RENAME_SET_DEFAULT NLCDESC > Description
      RENAME_SET_DEFAULT 3ALPHA > CRS
    MISSING_INPUT_ATTRS = REMOVE
    -> reproject-LL
reproject-LL: Reprojector
    DEST = LL-WGS84
    INTERPOLATION_TYPE_NAME = Nearest Neighbor
    RASTER_CELL_SIZE = Preserve Cells
    RASTER_TOLERANCE = 0.0
    REPROJECTED -> AttributeValueMapper_2
AttributeValueMapper_2
    DIRECTION = Forward (Source To Destination)
    LUT = Mar-05,MAR5105,Mar-24,MAR5124
    SRC = TIPLOC
    VAL_ATTR = _TIPLOC
    -> AttributeCreator_12
AttributeCreator_12
    ATTR_TABLE = SET_TO TIPLOC = FME_CONDITIONAL:DEFAULT_VALUE'@Value(TIPLOC)'BOOL_OP;OR;COMPOSITE_TEST;1;TEST _TIPLOC ATTRIBUTE_HAS_A_VALUE _FME_BLANK_STRING_'@Value(_TIPLOC)'FME_NUM_CONDITIONS2___
    -> AttributeRemover_8
AttributeRemover_8
    REMOVE_ATTRS = fid,NLC,NLCDESC16,UIC,_TIPLOC
    -> Green-woodpecker_2
Green-woodpecker_2: FeatureColorSetter
    COLOR = 0,1,0
    MODE = Fixed
    COLORED -> badDataFilter
Note: may have been some automated matching Grangetown(Cleveland) was snapped to Grangetown (south wales) / ditch it out of the Woodpecker data and pick it up from railmap instead
badDataFilter: TestFilter
    DEFAULT_VALUE = ok
    TEST_LIST = "BOOL_OP,OR,COMPOSITE_TEST,""""""1"""""",TEST_CLAUSE,CASE_INSENSITIVE_TEST @Value(TIPLOC) IN KRKP861,HIGHBYA,GRTN,BLUANCR,WROXHMR,MNTFLDS,ALBION,ALRSFRD,HRGY419,ECROYDN,SPEAPSS,REDHLS,TALRCEM,CRST428,CRST421,KSTP,HOTH343,STRHILL,PBRO612,PBRO552,PBRO544,PBRO534,ELGH225,ABIN521,ABINUS,ABIN528,CHTHAP,PLMD782,IVRN397,HYWRDNK,FELTDEP,LENH334,IVRN395,NNTN539,RTHG858,WNCF103,MLLNJN,RTHG888,BARKGLT,BEAL134,LYDNDGL,SLAT675,TERM182,WLNDNJN,WLNDNJW,IVRNBLC,HITC672,IMNGLL7,KGMRDDS,ABRGS38,DRTW68,BRAGJN,CARLNEC,NTHOPKJ,CRST423,WLWY182,LEED928,GRNGMRR,BLTCDRJ,BLTCWER",bad,"BOOL_OP,OR,COMPOSITE_TEST,""""""1"""""",TEST_CLAUSE,CASE_SENSITIVE_TEST @Value(TIPLOC) = BSAUWCP",coalWasher,"BOOL_OP,OR,COMPOSITE_TEST,""""""1"""""",TEST_CLAUSE,CASE_SENSITIVE_TEST @Value(TIPLOC) = KINBTLP",kinbraceTimber,"BOOL_OP,OR,COMPOSITE_TEST,""""""1"""""",TEST_CLAUSE,NUM_TEST @Value(STANOX) IN 79801",BadStanoxCode,"BOOL_OP,OR,COMPOSITE_TEST,""""""1"""""",TEST_CLAUSE,NUM_TEST @Value(STANOX) IN 8751,13045,13048,24428,36400,56120,58560,72283,82107,7802,82017",BadStanoxLocation
    coalWasher -> VertexCreator_3
    kinbraceTimber -> VertexCreator_5
    BadStanoxCode -> AttributeRemover_23
    ok -> FeatureJoiner_7 [LEFT]
    ok -> Junction_18
VertexCreator_3
    MEASURE_TYPE = Continuous
    MODE_NAME = Replace with Point
    XVAL = -1.8717
    YVAL = 54.7256
    -> FeatureJoiner_7 [LEFT]
VertexCreator_5
    MEASURE_TYPE = Continuous
    MODE_NAME = Replace with Point
    XVAL = -3.9411
    YVAL = 58.2546
    -> FeatureJoiner_7 [LEFT]
AttributeRemover_23
    REMOVE_ATTRS = STANOX,STANOXwp
    -> FeatureJoiner_7 [LEFT]
Junction_18
    -> AttributeKeeper_22
    -> FeatureJoiner_32 [RIGHT]
Note: https://railmap.azurewebsites.net/Downloads / licence: CC 4.0 / https://creativecommons.org/licenses/by-sa/4.0/
Note: TODO use these coordinates for Ireland
Note: Everything has TIPLOC- some blank STANOX
readerRailmap: FeatureReader
    ATTRIBUTES = JSONFeature,"ExportDate,ExportCount,Tiplocs{}.Name,Tiplocs{}.DisplayName,Tiplocs{}.Tiploc,Tiplocs{}.Stanox,Tiplocs{}.Latitude,Tiplocs{}.Longitude,Tiplocs{}.InBPlan,Tiplocs{}.InTPS,Tiplocs{}.NodeId,Tiplocs{}.Codes,Tiplocs{}.Details.BPlan_TimingPoint,Tiplocs{}.Details.TPS_StationType,Tiplocs{}.Details.TPS_StationCategory,Tiplocs{}.Details.CRS,Tiplocs{}.Details.Nalco,Tiplocs{}.Details.OffNetwork,Tiplocs{}.Details.ForceLPB,Tiplocs{}.Details.CompulsoryStop,Tiplocs{}.Details.UIC,Tiplocs{}.Details.Zone,Tiplocs{}.Elevation.Google,Tiplocs{}.Elevation.OpenElevation,Tiplocs{}.Elevation.OrdnanceSurvey5,Tiplocs{}.Elevation.OrdnanceSurvey50"
    ATTR_ACCUM_MODE = Only Use Result
    COMBINE_GEOM = Use Result
    COORDSYS = LL-WGS84
    DATASET = $(inputPath)\TiplocPublicExport_2023-06-15_12-06.json.gz
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> ListExploder
    INITIATOR -> OpenRailDataTiploc [INITIATOR]
ListExploder
    ATTR_ACCUM_MODE = Only Use List Attributes
    INDEX_ATTR = _element_index
    LIST_ATTR = Tiplocs{}
    ELEMENTS -> VertexCreator
VertexCreator
    MEASURE_TYPE = Continuous
    MODE_NAME = Replace with Point
    XVAL = @Value(Longitude)
    YVAL = @Value(Latitude)
    -> AttributeKeeper_10
AttributeKeeper_10
    CREATE_BULK_MODE_FEATURES = NO
    KEEP_ATTRS = Details.CRS,Stanox,Tiploc,Name
    -> Red-railmap_2
Red-railmap_2: FeatureColorSetter
    COLOR = 1,0,0
    MODE = Fixed
    COLORED -> createSource_railmap
createSource_railmap: AttributeCreator
    ATTR_TABLE = SET_TO dataSource = railmap
    -> badDataFilter_2
badDataFilter_2: TestFilter
    DEFAULT_VALUE = ok
    TEST_LIST = "BOOL_OP,OR,COMPOSITE_TEST,""""""1"""""",TEST_CLAUSE,CASE_INSENSITIVE_TEST @Value(Tiploc) IN CBOMDS,TESTSCR,GODALBN,WELSRHY,DONC108,ONIBURY,EBWVSGF,LLWRW2,EASTHAM,CRKLLAF,MANSNHS,EMBKMNT,GLNG26,CHAT65,KGMRUD1,CRGNTPS,WLBCGBR,HITC941,MRGMMID,XTEST01,XTEST02",bad,"BOOL_OP,OR,COMPOSITE_TEST,""""""1"""""",TEST_CLAUSE,NUM_TEST @Value(Stanox) IN 46245,87581",BadStanox
    ok -> AttributeCreator_8
    BadStanox -> AttributeRemover_22
AttributeRemover_22
    REMOVE_ATTRS = Stanox
    -> AttributeCreator_8
AttributeCreator_8
    ATTR_TABLE:
      SET_TO STANOX = @Value(Stanox)
      SET_TO TIPLOC = @Value(Tiploc)
      SET_TO Description = @Value(Name)
      SET_TO CRS = @Value(Details.CRS)
    -> Junction_19
    -> FeatureJoiner_8 [LEFT]
Junction_19
    -> AttributeKeeper_22
    -> FeatureJoiner_33 [RIGHT]
Note: https://wiki.openraildata.com/index.php/Identifying_Locations
OpenRailDataTiploc: FeatureReader
    ATTRIBUTES = TIPLOC,"TIPLOC,NAME,EASTING,NORTHING"
    ATTR_ACCUM_MODE = Only Use Result
    COMBINE_GEOM = Use Result
    COORDSYS = EPSG:27700
    DATASET = $(inputPath)\TIPLOC Eastings and Northings.xlsx
    FORMAT = XLSXR
    INTERACT = NONE
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = C:\Users\owenoneill\github\RAIL-CIF\TIPLOC Eastings and Northings.xlsx
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_READ_RASTER_MODE = None
    XLSXR_SCAN_MAX_FEATURES = 1000
    XLSXR_SCAN_SCHEMA_IF_DYNAMIC = No
    XLSXR_SCHEMA = TIPLOC,0,TIPLOC,char,9,,,1,NAME,char,30,,,2,EASTING,x_coordinate,,,,3,NORTHING,y_coordinate,,,,1,,,,NO,NO,1,C:\Users\owenoneill\github\RAIL-CIF\TIPLOC Eastings and Northings.xlsx,"0,0,3,9397",,NO,NO
    XLSXR_STRIP_SHEETNAME_SPACES = YES
    XLSXR_TABLELIST = TIPLOC
    XLSXR_TRIM_ATTR_NAME_WHITESPACE = Yes
    XLSXR_USE_SCHEMA_OTHER_FILES = No
    TIPLOC -> createSource_openRailData
    INITIATOR -> UK2GTFS-tiploc [INITIATOR]
createSource_openRailData: AttributeCreator
    ATTR_TABLE = SET_TO dataSource = openRailData
    -> Reprojector
Reprojector
    DEST = LL-WGS84
    INTERPOLATION_TYPE_NAME = Nearest Neighbor
    RASTER_CELL_SIZE = Preserve Cells
    RASTER_TOLERANCE = 0.0
    REPROJECTED -> AttributeRenamer_5
AttributeRenamer_5
    ATTR_TABLE:
      RENAME_SET_DEFAULT TIPLOC
      RENAME_SET_DEFAULT NAME > Description
    MISSING_INPUT_ATTRS = REMOVE
    -> colourBlue-openRailData_2
colourBlue-openRailData_2: FeatureColorSetter
    COLOR = 0,0,1
    MODE = Fixed
    COLORED -> badDataFilter_3
badDataFilter_3: TestFilter
    DEFAULT_VALUE = ok
    TEST_LIST:
      "BOOL_OP,AND,COMPOSITE_TEST,""""""1 AND 2"""""",TEST_CLAUSE,NUM_TEST @Value(EASTING) = 286200
      NUM_TEST @Value(NORTHING) = 931659",bad,"BOOL_OP,AND,COMPOSITE_TEST,""""""1 AND 2"""""",TEST_CLAUSE,NUM_TEST @Value(EASTING) = 260885
      NUM_TEST @Value(NORTHING) = 667397",bad,"BOOL_OP,OR,COMPOSITE_TEST,""""""1"""""",TEST_CLAUSE,CASE_INSENSITIVE_TEST @Value(TIPLOC) IN GRTN,RBRTRPG,WROXHMR,GLNG26,CBOMDS,IVRNBLC,CHAT65,HITC672,IMNGLL7,KGMRUD1,ABRGS38,DRTW68,CRGNTPS,WLBCGBR,CARLNEC,HITC941,MRGMMID,NTHOPKJ,CRST423,WLWY182,LEED928,GRNGMRR,BLTCDRJ,BLTCWER,BESTGBR,BEST931,BESTRR,BESTHST,BEST918,SWNACFC,SWNAGE,SWNAHMC,SWNAHNH,SWNAMGF,SWNANDN,TESTSCR,HRGY419",bad
    ok -> TestFilter_6
Note: TIPLOC may be confused with another location
TestFilter_6
    DEFAULT_VALUE = <UNFILTERED>
    TEST_LIST = "BOOL_OP,OR,COMPOSITE_TEST,""""""1"""""",TEST_CLAUSE,CASE_SENSITIVE_TEST @Value(TIPLOC) IN BEST344",bad
    bad -> AttributeRemover_20
    <UNFILTERED> -> AttributeRemover_9
AttributeRemover_20
    REMOVE_ATTRS = TIPLOC
    -> AttributeRemover_9
AttributeRemover_9
    REMOVE_ATTRS = EASTING,fme_fill_color,NORTHING
    -> Junction_20
    -> FeatureJoiner_9 [LEFT]
Junction_20
    -> AttributeKeeper_22
    -> FeatureJoiner_34 [RIGHT]
AttributeKeeper_22
    CREATE_BULK_MODE_FEATURES = NO
    KEEP_ATTRS = TIPLOC
    -> DuplicateFilter_11
DuplicateFilter_11
    INPUT_ORDERED_CHOICE = No
    KEYATTR = TIPLOC
    UNIQUE -> FeatureJoiner_32 [LEFT]
    UNIQUE -> FeatureJoiner_33 [LEFT]
    UNIQUE -> FeatureJoiner_34 [LEFT]
FeatureJoiner_32
    ATTR_CONFLICT_RES = Use Right
    GEOMETRY_HANDLING = Use Right
    JOIN_KEYS = TIPLOC TIPLOC STRING
    JOIN_MODE = Inner
    JOINED -> AttributeManager_4
    <REJECTED> -> dumpRejects_3
AttributeManager_4
    ATTR_TABLE:
      REMOVE Description
      REMOVE CRS
      REMOVE STANOX
      REMOVE STANOXwp
      REMOVE fme_fill_color
    -> Inspector_7
    -> AttributeRemover_3
    -> FeatureJoiner_2 [LEFT]
    -> AttributeKeeper
FeatureJoiner_33
    ATTR_CONFLICT_RES = Use Right
    GEOMETRY_HANDLING = Use Right
    JOIN_KEYS = TIPLOC TIPLOC STRING
    JOIN_MODE = Inner
    JOINED -> AttributeManager_5
    <REJECTED> -> dumpRejects_3
AttributeManager_5
    ATTR_TABLE:
      REMOVE fme_fill_color
      REMOVE Name
      REMOVE Tiploc
      REMOVE Stanox
      REMOVE Details.CRS
      REMOVE STANOX
      REMOVE Description
      REMOVE CRS
    -> AttributeRemover_5
    -> Inspector_7
    -> FeatureJoiner_2 [RIGHT]
    -> AttributeKeeper
FeatureJoiner_34
    ATTR_CONFLICT_RES = Use Right
    GEOMETRY_HANDLING = Use Right
    JOIN_KEYS = TIPLOC TIPLOC STRING
    JOIN_MODE = Inner
    JOINED -> AttributeManager_6
    <REJECTED> -> dumpRejects_3
AttributeManager_6
    ATTR_TABLE = REMOVE Description
    -> Inspector_7
    -> AttributeRemover_2
    -> AttributeRemover_4
FeatureJoiner_8
    ATTR_CONFLICT_RES = Use Left
    GEOMETRY_HANDLING = Use Left
    JOIN_KEYS = Tiploc TIPLOC STRING
    JOIN_MODE = Inner
    UNJOINED_LEFT -> Junction
    <REJECTED> -> Junction
Junction
    -> FeatureJoiner_21 [LEFT]
    -> FeatureJoiner_29 [LEFT]
FeatureJoiner_9
    ATTR_CONFLICT_RES = Use Left
    GEOMETRY_HANDLING = Use Left
    JOIN_KEYS = TIPLOC TIPLOC STRING
    JOIN_MODE = Inner
    UNJOINED_LEFT -> Junction_11
    <REJECTED> -> Junction_11
Junction_11
    -> FeatureJoiner_22 [LEFT]
    -> FeatureJoiner_28 [LEFT]
FeatureJoiner_7
    ATTR_CONFLICT_RES = Use Left
    GEOMETRY_HANDLING = Use Left
    JOIN_KEYS = TIPLOC TIPLOC STRING
    JOIN_MODE = Inner
    UNJOINED_LEFT -> Junction_9
    <REJECTED> -> Junction_9
Junction_9
    -> FeatureJoiner_23 [LEFT]
    -> FeatureJoiner_30 [LEFT]
dumpRejects_3: Inspector [off]
Note: https://itsleeds.github.io/UK2GTFS/ / https://github.com/ITSLeeds/UK2GTFS / https://github.com/ITSLeeds/UK2GTFS-data
UK2GTFS-tiploc: FeatureReader
    ATTRIBUTES = CSV,"stop_id,stop_code,stop_name,stop_lon,stop_lat"
    ATTR_ACCUM_MODE = Only Use Result
    COMBINE_GEOM = Use Result
    COORDSYS = LL-WGS84
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = stop_id,varchar(16),YES;stop_code,varchar(4),YES;stop_name,varchar(64),YES;stop_lon,x_coordinate,YES;stop_lat,y_coordinate,YES
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(inputPath)\tiplocs.csv
    FORMAT = CSV2
    INTERACT = NONE
    OUTPUT_FEATURES_DISPLAY = Schema and Data Features
    CSV -> createSource_UK2GTFS
    INITIATOR -> readBplanLoc [INITIATOR]
createSource_UK2GTFS: AttributeCreator
    ATTR_TABLE:
      SET_TO dataSource = UK2GTFS
      SET_TO stop_code = FME_CONDITIONAL:DEFAULT_VALUE'@Value(stop_code)'BOOL_OP;OR;COMPOSITE_TEST;1;CASE_SENSITIVE_TEST @Value(stop_code) = NA'FME_NULL_VALUE'FME_NUM_CONDITIONS2___
    -> AttributeRenamer_6
AttributeRenamer_6
    ATTR_TABLE:
      RENAME_SET_DEFAULT stop_code > CRS
      RENAME_SET_DEFAULT stop_name > Description
      RENAME_SET_DEFAULT stop_id > TIPLOC
    MISSING_INPUT_ATTRS = REMOVE
    -> StringReplacer_2
StringReplacer_2
    CASE = NO
    FIND_TEXT = \r|\n
    NO_MATCH = _FME_NO_OP_
    REGEXP = YES
    SRC_ATTRS = CRS,Description,TIPLOC
    -> colourYellow-UK2GTFS
colourYellow-UK2GTFS: FeatureColorSetter
    COLOR = 1,1,0
    MODE = Fixed
    COLORED -> badDataFilter_4
badDataFilter_4: TestFilter
    DEFAULT_VALUE = ok
    TEST_LIST:
      "BOOL_OP,AND,COMPOSITE_TEST,""""""1 AND 2"""""",TEST_CLAUSE,NUM_TEST @Value(stop_lon) = -3.94107
      NUM_TEST @Value(stop_lat) = 58.25884",bad,"BOOL_OP,AND,COMPOSITE_TEST,""""""1 AND 2"""""",TEST_CLAUSE,NUM_TEST @Value(stop_lon) = -4.22536
      NUM_TEST @Value(stop_lat) = 55.87958",bad,"BOOL_OP,OR,COMPOSITE_TEST,""""""1"""""",TEST_CLAUSE,CASE_INSENSITIVE_TEST @Value(TIPLOC) IN """,bad
    ok -> AttributeRemover_10
AttributeRemover_10
    REMOVE_ATTRS = fme_fill_color,stop_lat,stop_lon
    -> DuplicateFilter_2
DuplicateFilter_2
    INPUT_ORDERED_CHOICE = No
    KEYATTR = TIPLOC
    UNIQUE -> Junction_4
    UNIQUE -> FeatureJoiner_18 [LEFT]
    UNIQUE -> Junction_3
Junction_3
    -> FeatureJoiner_28 [RIGHT]
    -> FeatureJoiner_29 [RIGHT]
    -> FeatureJoiner_30 [RIGHT]
FeatureJoiner_30
    ATTR_CONFLICT_RES = Use Left
    GEOMETRY_HANDLING = Use Left
    JOIN_KEYS = TIPLOC TIPLOC STRING
    JOIN_MODE = Inner
    JOINED -> AttributeManager
    <REJECTED> -> dumped
AttributeManager
    ATTR_TABLE:
      REMOVE CRS
      REMOVE STANOX
      REMOVE STANOXwp
      REMOVE fme_fill_color
      REMOVE fme_rejection_code
      REMOVE fme_rejection_message
    -> Junction_6
FeatureJoiner_29
    ATTR_CONFLICT_RES = Use Left
    GEOMETRY_HANDLING = Use Left
    JOIN_KEYS = TIPLOC TIPLOC STRING
    JOIN_MODE = Inner
    JOINED -> AttributeManager_2
    <REJECTED> -> dumped
AttributeManager_2
    ATTR_TABLE:
      REMOVE Name
      REMOVE Tiploc
      REMOVE Stanox
      REMOVE Details.CRS
      REMOVE fme_fill_color
      REMOVE fme_rejection_code
      REMOVE fme_rejection_message
      REMOVE STANOX
      REMOVE CRS
    -> Junction_7
FeatureJoiner_28
    ATTR_CONFLICT_RES = Use Left
    GEOMETRY_HANDLING = Use Left
    JOIN_KEYS = TIPLOC TIPLOC STRING
    JOIN_MODE = Inner
    JOINED -> AttributeManager_3
    <REJECTED> -> dumped
AttributeManager_3
    ATTR_TABLE:
      REMOVE fme_rejection_code
      REMOVE fme_rejection_message
    -> Junction_8
Junction_15
    -> AttributeRemover_14
    -> AttributeRemover_16
Junction_5
    -> AttributeRemover_7
    -> AttributeRemover_13
Junction_2
    -> FeatureJoiner_24 [RIGHT]
    -> FeatureJoiner_25 [RIGHT]
    -> FeatureJoiner_26 [RIGHT]
dumpRejects: Inspector [off]
dumped: Inspector [off]
Junction_4
    -> AttributeRemover_6
    -> AttributeRemover_15
FeatureJoiner_18
    ATTR_CONFLICT_RES = Use Left
    GEOMETRY_HANDLING = Use Left
    JOIN_KEYS = TIPLOC TIPLOC STRING
    JOIN_MODE = Inner
    UNJOINED_LEFT -> joinTiploc_6 [RIGHT]
DuplicateFilter_5
    INPUT_ORDERED_CHOICE = No
    KEYATTR = _x _y
    UNIQUE -> AttributeKeeper_21
AttributeKeeper_21
    CREATE_BULK_MODE_FEATURES = NO
    KEEP_ATTRS = TIPLOC
    -> Bufferer
Bufferer
    ANGLE = 22.5
    CAP_STYLE = Arc
    CORNER_STYLE = Arc
    MODE = AREA
    OFFSET = 5
    OFFSET_UNITS = METERS
    PRECISION = APPROX
    BUFFERED -> Reprojector_2
Reprojector_2
    DEST = LL-WGS84
    INTERPOLATION_TYPE_NAME = Nearest Neighbor
    RASTER_CELL_SIZE = Preserve Cells
    RASTER_TOLERANCE = 0.0
    REPROJECTED -> SpatialFilter_3 [Filter]
    REPROJECTED -> SpatialFilter_2 [Filter]
    REPROJECTED -> SpatialFilter [Filter]
FeatureJoiner_23
    ATTR_CONFLICT_RES = Use Left
    GEOMETRY_HANDLING = Use Left
    JOIN_KEYS = TIPLOC TIPLOC STRING
    JOIN_MODE = Inner
    UNJOINED_LEFT -> joinTiploc_3 [RIGHT]
    <REJECTED> -> joinTiploc_3 [RIGHT]
FeatureJoiner_21
    ATTR_CONFLICT_RES = Use Left
    GEOMETRY_HANDLING = Use Left
    JOIN_KEYS = TIPLOC TIPLOC STRING
    JOIN_MODE = Inner
    UNJOINED_LEFT -> joinTiploc_4 [RIGHT]
    <REJECTED> -> joinTiploc_4 [RIGHT]
FeatureJoiner_22
    ATTR_CONFLICT_RES = Use Left
    GEOMETRY_HANDLING = Use Left
    JOIN_KEYS = TIPLOC TIPLOC STRING
    JOIN_MODE = Inner
    UNJOINED_LEFT -> joinTiploc_5 [RIGHT]
    <REJECTED> -> joinTiploc_5 [RIGHT]
Note: https://wiki.openraildata.com/index.php/BPLAN_data_structure / https://wiki.openraildata.com/index.php?title=BPLAN_Geography_Data
readBplanLoc: FeatureReader
    ATTRIBUTES = BPLAN.bplan.loc,"LocationCode,LocationName,StartDate,EndDate,OsEasting,OsNorthing,TimingPointType,Zone,StanoxCode,OffNetworkIndicator,ForceLPB"
    ATTR_ACCUM_MODE = Only Use Result
    COMBINE_GEOM = Use Result
    COORDSYS = EPSG:27700
    DATASET = LocalSqlServer
    FEATURETYPES = BPLAN.bplan.loc
    FORMAT = MSSQL_ADO
    MSSQL_ADO_APPLICATION_INTENT = ReadOnly
    MSSQL_ADO_COMMAND_TIMEOUT = 30
    MSSQL_ADO_CREATE_FEATURE_TABLES_FROM_DATA = Yes
    MSSQL_ADO_NAMED_CONNECTION = LocalSqlServer
    MSSQL_ADO_QUERY_FEATURE_TYPES_FOR_MERGE_FILTERS = Yes
    MSSQL_ADO_READ_CACHE_SIZE = 10000
    OUTPUT_FEATURES_DISPLAY = Schema and Data Features
    BPLAN.bplan.loc -> createSource_BPLAN
    INITIATOR -> readCountryOutlines [INITIATOR]
createSource_BPLAN: AttributeCreator
    ATTR_TABLE = SET_TO dataSource = BPLAN
    -> tagBadCoords
tagBadCoords: AttributeCreator
    ATTR_TABLE = SET_TO GeometryQualityCode = FME_CONDITIONAL:DEFAULT_VALUE'_FME_NO_OP_'BOOL_OP;OR;COMPOSITE_TEST;1 OR 2 OR 3 OR 4;NUM_TEST @Value(OsEasting) <= 1;NUM_TEST @Value(OsNorthing) <= 1;NUM_TEST @Value(OsEasting) >= 999999;NUM_TEST @Value(OsNorthing) >= 999999'NULL'BOOL_OP;OR;COMPOSITE_TEST;1;NUM_TEST @Value(OsEasting) = 10000'EastingEire'BOOL_OP;AND;COMPOSITE_TEST;1 AND 2;NUM_TEST @Value(OsEasting) = 99999;NUM_TEST @Value(OsNorthing) = 99999'NULL5'FME_NUM_CONDITIONS4___
    -> badCoords
badCoords: TestFilter
    DEFAULT_VALUE = Good(ish)
    TEST_LIST = "BOOL_OP,OR,COMPOSITE_TEST,""""""1"""""",TEST_CLAUSE,CASE_SENSITIVE_TEST @Value(LocationCode) IN WANTMPL,AMNG488,THYMGBR,ALRSFRD",BadStanox,"BOOL_OP,OR,COMPOSITE_TEST,""""""1"""""",TEST_CLAUSE,CASE_SENSITIVE_TEST @Value(LocationCode) IN PIACNZA,DNKIRK,GRNLUDR",Bad,"BOOL_OP,OR,COMPOSITE_TEST,""""""1"""""",TEST_CLAUSE,CASE_SENSITIVE_TEST GeometryQualityCode ATTRIBUTE_HAS_A_VALUE """,Bad
    Bad -> GeometryRemover
    BadStanox -> AttributeRemover_21
    Good(ish) -> VertexCreator_2
AttributeRemover_21
    REMOVE_ATTRS = StanoxCode
    -> GeometryRemover
VertexCreator_2
    MEASURE_TYPE = Continuous
    MODE_NAME = Replace with Point
    XVAL = @Value(OsEasting)
    YVAL = @Value(OsNorthing)
    -> clipCountry_2 [CLIPPEE]
readCountryOutlines: FeatureReader
    ATTRIBUTES = boundary.mv_tbl__ons_gb_country_2021_out_mv_ply__0,"id,ctry_cd,ctry_nm,ons_year,country_id,ons_gb_country_in_ply_oid,num_rec"
    ATTR_ACCUM_MODE = Only Use Result
    COMBINE_GEOM = Use Result
    DATASET = tfwm_redshift_dw_prod_readonly
    FEATURETYPES = boundary.mv_tbl__ons_gb_country_2021_out_mv_ply__0
    FORMAT = REDSHIFT_SPATIAL
    INTERACT = NONE
    OUTPUT_FEATURES_DISPLAY = Schema and Data Features
    REDSHIFT_SPATIAL_CREATE_FEATURE_TABLES_FROM_DATA = Yes
    REDSHIFT_SPATIAL_DISABLE_COLLECTION_SPLITTING = yes
    REDSHIFT_SPATIAL_FEATURES_PER_FETCH = 10000
    REDSHIFT_SPATIAL_NAMED_CONNECTION = tfwm_redshift_dw_prod_readonly
    REDSHIFT_SPATIAL_QUERY_FEATURE_TYPES_FOR_MERGE_FILTERS = Yes
    REDSHIFT_SPATIAL_READ_GEOMETRY_AS = HEX_ENCODED_WKB
    REDSHIFT_SPATIAL_READ_TIME_WITH_TIMEZONE = Yes
    REDSHIFT_SPATIAL_SCHEMAS_FOR_TABLE_LISTING = boundary
    REDSHIFT_SPATIAL_USE_SEARCH_ENVELOPE = NO
    REDSHIFT_SPATIAL_USE_TRUE_POSTGIS_TYPES = yes
    boundary.mv_tbl__ons_gb_country_2021_out_mv_ply__0 -> reproject-LL_4
    boundary.mv_tbl__ons_gb_country_2021_out_mv_ply__0 -> Bufferer_2
    INITIATOR -> CORPUS [INITIATOR]
reproject-LL_4: Reprojector
    DEST = LL-WGS84
    INTERPOLATION_TYPE_NAME = Nearest Neighbor
    RASTER_CELL_SIZE = Preserve Cells
    RASTER_TOLERANCE = 0.0
    REPROJECTED -> clipCountry [CLIPPER]
clipCountry: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeRenamer_8
AttributeRenamer_8
    ATTR_TABLE:
      RENAME_SET_DEFAULT abbrev > TIPLOC
      RENAME_SET_DEFAULT longname > Description
      RENAME_SET_DEFAULT stanox > STANOX
      RENAME_SET_DEFAULT crscode > CRS
    MISSING_INPUT_ATTRS = REMOVE
    -> joinTiploc_8 [RIGHT]
DuplicateFilter_8 [off]
    INPUT_ORDERED_CHOICE = No
    KEYATTR = TIPLOC
Bufferer_2
    ANGLE = 22.5
    CAP_STYLE = Round
    CORNER_STYLE = Round
    MODE = AREA
    OFFSET = 1000
    OFFSET_UNITS = METERS
    PRECISION = APPROX
    BUFFERED -> clipCountry_2 [CLIPPER]
clipCountry_2: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeCreator_4
    OUTSIDE -> GeometryRemover
GeometryRemover
    -> AttributeCreator_4
AttributeCreator_4
    ATTR_TABLE:
      SET_TO TIPLOC = @Value(LocationCode)
      SET_TO STANOX = @Value(StanoxCode)
      SET_TO Description = @Value(LocationName)
    -> reproject-LL_3
reproject-LL_3: Reprojector
    DEST = LL-WGS84
    INTERPOLATION_TYPE_NAME = Nearest Neighbor
    RASTER_CELL_SIZE = Preserve Cells
    RASTER_TOLERANCE = 0.0
    REPROJECTED -> AttributeRemover_11
AttributeRemover_11
    REMOVE_ATTRS = EndDate,ForceLPB,GeometryQualityCode,OffNetworkIndicator,OsEasting,OsNorthing,StartDate,TimingPointType,Zone
    -> joinTiploc_7 [RIGHT]
Note: https://wiki.openraildata.com/index.php?title=Reference_Data / https://publicdatafeeds.networkrail.co.uk/ntrod/SupportingFileAuthenticate?type=CORPUS
CORPUS: FeatureReader
    ATTRIBUTES = CSV,"TIPLOCDATA.STANOX,TIPLOCDATA.TIPLOC,TIPLOCDATA.3ALPHA,TIPLOCDATA.NLCDESC"
    ATTR_ACCUM_MODE = Only Use Result
    COMBINE_GEOM = Use Result
    COORDSYS = LL-WGS84
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = TIPLOCDATA.NLC,real64,NO;TIPLOCDATA.STANOX,varchar(6),YES;TIPLOCDATA.TIPLOC,varchar(16),YES;TIPLOCDATA.3ALPHA,varchar(4),YES;TIPLOCDATA.UIC,varchar(6),NO;TIPLOCDATA.NLCDESC,varchar(64),YES;TIPLOCDATA.NLCDESC16,varchar(22),NO
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(inputPath)\CORPUS.csv
    FORMAT = CSV2
    INTERACT = NONE
    OUTPUT_FEATURES_DISPLAY = Schema and Data Features
    CSV -> createSource_CORPUS
createSource_CORPUS: AttributeCreator
    ATTR_TABLE:
      SET_TO dataSource = CORPUS
      SET_TO TIPLOCDATA.3ALPHA = FME_CONDITIONAL:DEFAULT_VALUE'@Value(TIPLOCDATA.3ALPHA)'BOOL_OP;OR;COMPOSITE_TEST;1;CASE_SENSITIVE_TEST @Value(TIPLOCDATA.3ALPHA) = NA'FME_NULL_VALUE'FME_NUM_CONDITIONS2___
      SET_TO TIPLOCDATA.TIPLOC = FME_CONDITIONAL:DEFAULT_VALUE'@Value(TIPLOCDATA.TIPLOC)'BOOL_OP;OR;COMPOSITE_TEST;1;CASE_SENSITIVE_TEST @Value(TIPLOCDATA.TIPLOC) = NA'FME_NULL_VALUE'FME_NUM_CONDITIONS2___
      SET_TO TIPLOCDATA.STANOX = FME_CONDITIONAL:DEFAULT_VALUE'@Value(TIPLOCDATA.STANOX)'BOOL_OP;OR;COMPOSITE_TEST;1;CASE_SENSITIVE_TEST @Value(TIPLOCDATA.STANOX) = NA'FME_NULL_VALUE'FME_NUM_CONDITIONS2___
      SET_TO TIPLOCDATA.NLCDESC = FME_CONDITIONAL:DEFAULT_VALUE'@Value(TIPLOCDATA.NLCDESC)'BOOL_OP;OR;COMPOSITE_TEST;1;CASE_SENSITIVE_TEST @Value(TIPLOCDATA.NLCDESC) = NA'FME_NULL_VALUE'FME_NUM_CONDITIONS2___
    -> DuplicateFilter_3
DuplicateFilter_3
    INPUT_ORDERED_CHOICE = No
    KEYATTR = TIPLOCDATA.STANOX TIPLOCDATA.TIPLOC
    UNIQUE -> badCoords_3
badCoords_3: TestFilter
    DEFAULT_VALUE = Good(ish)
    TEST_LIST = "BOOL_OP,OR,COMPOSITE_TEST,""""""1"""""",TEST_CLAUSE,NUM_TEST @Value(TIPLOCDATA.STANOX) IN 79801,87018",BadStanoxCode
    BadStanoxCode -> AttributeRemover_25
    Good(ish) -> AttributeCreator_10
AttributeRemover_25
    REMOVE_ATTRS = TIPLOCDATA.STANOX
    -> AttributeCreator_10
AttributeCreator_10
    ATTR_TABLE:
      SET_TO STANOX = @Value(TIPLOCDATA.STANOX)
      SET_TO TIPLOC = @Value(TIPLOCDATA.TIPLOC)
      SET_TO CRS = @Value(TIPLOCDATA.3ALPHA)
      SET_TO Description = @Value(TIPLOCDATA.NLCDESC)
    -> joinTiploc_9 [RIGHT]
DuplicateFilter_10 [off]
    INPUT_ORDERED_CHOICE = No
    KEYATTR = TIPLOC
AttributeCreator_15
    ATTR_TABLE = SET_TO STANOX-group = @Evaluate(@int(@Value(STANOX)/1000))
    -> AttributeRangeFilter
    -> AttributeKeeper_30
AttributeKeeper_30
    CREATE_BULK_MODE_FEATURES = NO
    KEEP_ATTRS = STANOX-group
    -> VertexExtractor_10
VertexExtractor_10
    Point -> Reprojector_3
Reprojector_3
    DEST = EPSG:27700
    INTERPOLATION_TYPE_NAME = Nearest Neighbor
    RASTER_CELL_SIZE = Preserve Cells
    RASTER_TOLERANCE = 0.0
    REPROJECTED -> LineBuilder_7
LineBuilder_7
    ACCUM_INPUT_ATTRS = Use Attributes From One Feature
    GROUP_BY = STANOX-group
    REMOVE_DUPLICATES = No
    LINE -> MinimumSpanningCircleReplacer
MinimumSpanningCircleReplacer
    MODE = Set Attributes
    RADIUS = _radius
    XCENTER = _center_x
    YCENTER = _center_y
    -> AttributeKeeper_31
AttributeKeeper_31
    CREATE_BULK_MODE_FEATURES = NO
    KEEP_ATTRS = _radius,STANOX-group
    -> TestFilter_7
TestFilter_7
    DEFAULT_VALUE = <UNFILTERED>
    TEST_LIST:
      "BOOL_OP,OR,COMPOSITE_TEST,""""""1"""""",TEST_CLAUSE,NUM_TEST @Value(STANOX-group) = 0",Europe,"BOOL_OP,AND,COMPOSITE_TEST,""""""1 AND 2"""""",TEST_CLAUSE,NUM_TEST @Value(STANOX-group) = 1
      NUM_TEST @Value(_radius) <= 120000",NorthernScotland,"BOOL_OP,OR,COMPOSITE_TEST,""""""1"""""",TEST_CLAUSE,NUM_TEST @Value(_radius) > 100000",100km+
    100km+ -> Terminator_2
Terminator_2
    MESSAGE:
      Translation Terminated

      Bigger than 100km STANOX zone
AttributeRangeFilter
    IN_ATTR = STANOX-group
    LUT = 0,0,0: Mainland Europe,1,1,1: Thurso, Kyle, Inverness, Nairn, Dalwhinnie,2,2,2: Elgin, Aberdeen, Stonehaven,3,3,3: Laurencekirk, Dundee, Blair Atholl, Perth, Dunblane, Kirkcaldy, Dunfermline, Stirling, Inverkeithing,4,4,4: Bathgate, Fauldhouse, West Calder, Auchengray, Dalmeny, Edinburgh, Dunbar, Marshall Meadows,5,5,5: Larbert, Greenhill, Falkirk, Grangemouth, Linlithgow, Winchburgh Jn,6,6,6: Mallaig, Fort William, Oban, Helensburgh, Dalmuir, Glasgow Queen St, Croy, Gartcosh, Blairhill,7,7,7: Wemyss Bay, Lochwinnoch, Paisley, Lugton, Neilston, Glasgow Central, Coatbridge, Airdrie, Cumbernauld, Motherwell, Quintinshill,8,8,8: Glengarnock, Largs, Ayr, Stranraer, Kilmarnock, Sanquhar,9,9,9: Dumfries, Gretna Jn, Carlisle, Wigton, Tebay, Hellifield, Skipton,10,10,10: Aspatria, Workington, Sellafield,11,11,11: Windermere, Barrow-in-Furness, Carnforth, Giggleswick, Lancaster,12,12,12: Berwick-Upon-Tweed, North Blyth, Newcastle, King Edward Bridges Jn,13,13,13: Tyne Dock, Heworth, Wetherall, Tyne Yard, Durham, Tursdale Jn,14,14,14: Boldon West Jn, Sunderland, Hartlepool,15,15,15: Port Clarence, Billingham, Ferryhill, Middlesborough, Whitby, Pickering (NYMR), Saltburn, Bishop Auckland, Darlington, Northallerton,16,16,16: Thirsk, Harrogate, Scarborough, York, Temple Hirst Jn, Garforth, Selby, Ferrybridge, Castleford,17,17,17: Cononley, Keighley, Bradford Forster Square, Leeds, Pannal, Cross Gates, Stourton, Altofts Jn, Drax,18,18,18: Drax, Eggborough, Knottingley, Wakefield, Moorethorpe, Darton, Huddersfield, Marsden, Hebden Bridge, Bradford Interchange,19,19,19: Filey, Bridlington, Beverely, Hull, Gilberbdyke, Wressle,20,20,20: Goole, Thorne North,21,21,21: Barton-on-Humber, Grimsby, Cleethorpes, Immingham, Barnetby, Wraby Jn,22,22,22: Scunthorpe, Althorpe,23,23,23: Crowle, Heck, Adwick, Doncaster, Retford,24,24,24: Thurnscoe, Connisbrough, Swinton, Barnsley, Rotherham Central,25,25,25: Masborough, Sheffield, Dodworth, Penistone, Dore, Woodhouse, Beighton Jn,26,26,26: Brigg, Gainsborough, West Burton, Worksop, Whitwell, Kiveton Bridge,27,27,27: Oxcroft, Bolsover, Barrow Hill, Chesterfield,28,28,28: Cresswell, Shirebrook, Thoresby, High Marnham,29,29,29: Hall Royd Jn, Burnley, Colne, Citheroe, Blackburn, Pleasington, Hall'i'th Wood,30,30,30: Blackpool, Preston, Euxton Balshaw Lane, Lostock Jn,31,31,31: Rawtenstall (ELR), Todmorden, Manchester Victoria, Bolton, Patricroft,32,32,32: Manchester Piccadilly, Stalybridge, Diggle Jn, Hadfield, Stockport, New Mills, Dove Holes, Manchester Airport, Chelford, Macclesfield,33,33,33: Trafford Park, Manchester Oxford Road, Irlam,34,34,34: Chinley, Hope, Grindleford, Buxton, Peak Forest, Tunstead, Hindlow,35,35,35: Southport, Wigan, Swinton, Warrington Bank Quay, St Helens, Frodsham,36,36,36: Ormskirk, Birkdale, Liverpool, Runcorn, Huyton, Warrington Central, Glazebrook,37,37,37: Acton Bridge, Mouldsworth, Northwich, Altrincham, Middlewich,38,38,38: West Kirby, New Brighton, Neston, Birkenhead, Liverpool Central, Ellesmere Port, Helsby,39,39,39: Dee Marsh, Shotton Paper, Hawarden Bridge,40,40,40: Holyhead, Llandudno, Chester, Mickle Trafford,41,41,41: Shotton High Level, Wrexham, Chirk,42,42,42: Goostrey, Crewe, Yorton, Norton Bridge, Alsager,43,43,43: Congleton, Stoke-on-Trent, Stafford, Rugeley T.V., Armitage Jn, Oakamoor, Uttoxeter,44,44,44: Saxilby, Lincoln, Market Rasen, Sleaford, Skegness, Newark, Grantham, Stoke Jn,45,45,45: Tallington, Stamford, Peterborough, Biggleswade,46,46,46: Spalding, Whittlesea, March, Kings Lynn, Thetford, Ely, Bury St Edmunds, Elmswell,47,47,47: Newmarket, Waterbeach, Cambridge, Meldreth, Stansted Airport, Roydon,48,48,48: Sheringham, Great Yarmouth, Lowestoft, Norwich, Harling Road,49,49,49: Diss, Oulton Broad South, Felixstowe, Ipswich, Manningtree, Harwich,50,50,50: Walton-on-Naze, Clacton, Colchester, Sudbury, Braintree, Southminster, Southend Victoria, Shenfield, Ilford, Maryland,51,51,51: Shoeburyness, Southend Central, Tilbury, Upminster, Barking, Woodgrange Park, Crouch Hill, Hertford East, Enfield Town, Severn Sisters,52,52,52: Hackney Wick, Caledonian Road & Barnsbury, Temple Mills, Stratford, North Woolwich, West Ham, Fenchurch Street, Chingford, Liverpool St,53,53,53: Royston, Arlesley, Stevenage, Hertford North, Bowes Park, Welwyn Garden City, Brookman Park,54,54,54: Potters Bar, Bounds Green, Finsbury Park, Moorgate (GN), Kings Cross,55,55,55: Newstead, Attenborough, Nottingham, Rolleston, Bingham,56,56,56: Clay Cross, Alftreton, Mansfield Woodhouse, Langley Mill, Toton, Long Eaton, Trent, Ratcliffe Power Stn, Castle Donnington,57,57,57: Matlock, Belper, Derby, Spondon, Tutbury & Hatton, Burton-on-Trent, Barton-Under-Needlewood,58,58,58: Coalville, Bardon Hill, Stud Farm,59,59,59: Loughborough, Oakham, Leicester, Hinckley, Market Harborough,60,60,60: Corby,61,61,61: Kettering, Wellingborough,62,62,62: Bedford, Fenny Stratford, Luton, Harpenden,63,63,63: Northolt Park, Marylebone, St Albans, Cricklewood, West Hampstead, St Pancras, Farringdon, Moorgate,64,64,64: Gobowen, Shrewsbury, Church Stretton, Pwllheli, Aberystwyth, Wellington, Ironbridge Power Stn,65,65,65: Penkridge, Shifnal, Wolverhampton, Lichfield, Rugeley Town, Walsall, Birmingham New St, Stourbridge, Harltlebury,66,66,66: Tamworth H.L., Daw Mill, Washwood Heath, Saltley, Birmingham Snow Hill, Warwick, Stratford-Upon-Avon, Redditch,67,67,67: Bromsgrove, Worcester, Ledbury, Moreton-in-Marsh,68,68,68: Ashchurch, Gloucester, Sharpness, Stroud,69,69,69: Tamworth, L.L. Nuneaton, Coventry, Birmingham International, Leamington Spa, Banbury, Haddenham & Thame Parkway,70,70,70: Rugby, Northampton, Bletchley, Aylesbury, Harrow-on-the-Hill, Berkhamsted,71,71,71: Hemel Hempsted, St Albans Abbey, Watford, Croxley Green,72,72,72: Watford High Street, Wembley Central, Willesden, North Pole, West Brompton, Euston, Gospel Oak, Camden Road,73,73,73: Paddington, Greenford, Princess Risborough, Southall, Heathrow Airport, Slough, Windsor & Eton C.Burnham,74,74,74: Taplow, Maidenhead, Marlow, Henley-on-Thames, Reading, Didcot, Uffington, Oxford, Bicester Town, Heyford, Pewsey,75,75,75: Swindon, Kemble, Chippenham, Melksham,76,76,76: Lydney, Llanwern, Craven Arms, Hereford, Newport, Ebbw Vale,77,77,77: Pengam FLT, Cardiff Docks, Cardiff Central,78,78,78: Trehebert, Rhymney, Cardiff Queen Street, Cardiff Bay, Cardiff Canton, Pontyclun, Penarth, Barry, Llantwit Major,79,79,79: Kidwelly, Llanelli, Broome, Swansea, Port Talbot, Bridgend, Pencoed, Maesteg,80,80,80: Fishguard Harbour, Milford Haven, Pembrook Dock, Carmarthen,81,81,81: Hullavington, Yate, Pilning, Bath, Bristol, Bridgewater,82,82,82: Freshford, Westbury, Castle Cary, Yeovil, Maiden Newton, Yeovil Jn, Tisbury,83,83,83: Taunton, Minehead, Barnstaple, Oakhampton, Exeter, Crewekerne, Exmouth, Paignton, Totnes,84,84,84: Ivybridge, Plymouth, Gunnislake, Liskeard, Looe, Largin,85,85,85: Bodmin Parkway, Fowey, Newquay, Falmouth, St Ives, Penzance,86,86,86: Esher, Chertsey, Basingstoke, Mortimer, Eastleigh, Salisbury, Isle of Wight, Portsmouth, Littlehampton, Southampton, Weymouth,87,87,87: Winnersh, Alton, Guildford, Rowlands Castle, Waterloo, Victoria, City Thameslink, London Bridge, Uckfield, Brighton, Arundel, Angemering,88,88,88: Hove, Plumpton, Eastbourne, Hastings, Winchelsea, Charing Cross, Cannon St, Nunhead, West Dulwich, Lewisham, Hayes, Chelfield, Sole St, Strood,89,89,89: Rochester, Knockholt, Otford, Seven Oaks, Tonbridge, Ashford, Rye, Dover, Folkestone, Dollands Moor

Bookmark: joining
Note: Take geometry for Liz line from ATCO
joinTiploc: FeatureJoiner
    ATTR_CONFLICT_RES = Use Left
    GEOMETRY_HANDLING = Use Right
    JOIN_KEYS = TIPLOC TIPLOC STRING
    JOIN_MODE = Inner
    JOINED -> AttributeCreator_6
    UNJOINED_RIGHT -> joinTiploc_2 [RIGHT]
joinTiploc_2: FeatureJoiner
    ATTR_CONFLICT_RES = Use Left
    GEOMETRY_HANDLING = Use Left
    JOIN_KEYS = TIPLOC TIPLOC STRING
    JOIN_MODE = Inner
    JOINED -> AttributeCreator_6
    UNJOINED_LEFT -> keepOutputAttributes
    UNJOINED_RIGHT -> keepOutputAttributes
    <REJECTED> -> keepOutputAttributes
Note: Take CRS from ATOC, / this means that stations with multiple TIPLOCs get the same CRS code
AttributeCreator_6
    ATTR_TABLE = SET_TO CRS = FME_CONDITIONAL:DEFAULT_VALUE'@Value(CRS)'BOOL_OP;OR;COMPOSITE_TEST;1;TEST CRS Code ATTRIBUTE_HAS_A_VALUE _FME_BLANK_STRING_'@Value(CRS Code)'FME_NUM_CONDITIONS2___
    -> keepOutputAttributes
keepOutputAttributes: AttributeKeeper
    CREATE_BULK_MODE_FEATURES = NO
    KEEP_ATTRS = CRS,dataSource,Description,STANOX,TIPLOC
    -> joinTiploc_8 [LEFT]
joinTiploc_8: FeatureJoiner
    ATTR_CONFLICT_RES = Use Left
    GEOMETRY_HANDLING = Use Left
    JOIN_KEYS = TIPLOC TIPLOC STRING
    JOIN_MODE = Inner
    JOINED -> keepOutputAttributes_7
    UNJOINED_LEFT -> keepOutputAttributes_7
    UNJOINED_RIGHT -> keepOutputAttributes_7
    <REJECTED> -> keepOutputAttributes_7
keepOutputAttributes_7: AttributeKeeper
    CREATE_BULK_MODE_FEATURES = NO
    KEEP_ATTRS = CRS,dataSource,Description,STANOX,TIPLOC
    -> joinTiploc_3 [LEFT]
joinTiploc_3: FeatureJoiner
    ATTR_CONFLICT_RES = Use Left
    GEOMETRY_HANDLING = Use Left
    JOIN_KEYS = TIPLOC TIPLOC STRING
    JOIN_MODE = Inner
    JOINED -> AttributeCreator_11
    JOINED -> keepOutputAttributes_2
    UNJOINED_LEFT -> keepOutputAttributes_2
    UNJOINED_RIGHT -> keepOutputAttributes_2
    <REJECTED> -> keepOutputAttributes_2
Note: leave STANOX that have come from above blank - fill in from CORPUS
AttributeCreator_11 [off]
    ATTR_TABLE = SET_TO STANOX = FME_CONDITIONAL:DEFAULT_VALUE'@Value(STANOX)'BOOL_OP;OR;COMPOSITE_TEST;1 OR 2 OR 3;CASE_SENSITIVE_TEST STANOX ATTRIBUTE_IS_EMPTY _FME_BLANK_STRING_;CASE_SENSITIVE_TEST STANOX ATTRIBUTE_VALUE_NULL _FME_BLANK_STRING_;CASE_SENSITIVE_TEST STANOX ATTRIBUTE_IS_MISSING _FME_BLANK_STRING_'@Value(STANOXwp)'FME_NUM_CONDITIONS2___
    -> keepOutputAttributes_2
keepOutputAttributes_2: AttributeKeeper
    CREATE_BULK_MODE_FEATURES = NO
    KEEP_ATTRS = CRS,dataSource,Description,STANOX,TIPLOC,fme_color
    -> joinTiploc_4 [LEFT]
    -> DuplicateFilter_9
DuplicateFilter_9 [off]
    INPUT_ORDERED_CHOICE = No
    KEYATTR = TIPLOC
joinTiploc_4: FeatureJoiner
    ATTR_CONFLICT_RES = Use Left
    GEOMETRY_HANDLING = Use Left
    JOIN_KEYS = TIPLOC TIPLOC STRING
    JOIN_MODE = Inner
    JOINED -> AttributeCreator_3
    UNJOINED_LEFT -> keepOutputAttributes_3
    UNJOINED_RIGHT -> keepOutputAttributes_3
    <REJECTED> -> keepOutputAttributes_3
AttributeCreator_3
    ATTR_TABLE:
      SET_TO STANOX = FME_CONDITIONAL:DEFAULT_VALUE'@Value(STANOX)'BOOL_OP;OR;COMPOSITE_TEST;1 OR 2 OR 3;CASE_SENSITIVE_TEST STANOX ATTRIBUTE_IS_EMPTY _FME_BLANK_STRING_;CASE_SENSITIVE_TEST STANOX ATTRIBUTE_VALUE_NULL _FME_BLANK_STRING_;CASE_SENSITIVE_TEST STANOX ATTRIBUTE_IS_MISSING _FME_BLANK_STRING_'@Value(Stanox)'FME_NUM_CONDITIONS2___
      SET_TO TIPLOC = FME_CONDITIONAL:DEFAULT_VALUE'@Value(TIPLOC)'BOOL_OP;OR;COMPOSITE_TEST;1 OR 2 OR 3;CASE_SENSITIVE_TEST TIPLOC ATTRIBUTE_IS_EMPTY _FME_BLANK_STRING_;CASE_SENSITIVE_TEST TIPLOC ATTRIBUTE_VALUE_NULL _FME_BLANK_STRING_;CASE_SENSITIVE_TEST TIPLOC ATTRIBUTE_IS_MISSING _FME_BLANK_STRING_'@Value(Tiploc)'FME_NUM_CONDITIONS2___
      SET_TO CRS = FME_CONDITIONAL:DEFAULT_VALUE'@Value(CRS)'BOOL_OP;OR;COMPOSITE_TEST;1 OR 2 OR 3;CASE_SENSITIVE_TEST CRS ATTRIBUTE_IS_EMPTY _FME_BLANK_STRING_;CASE_SENSITIVE_TEST CRS ATTRIBUTE_VALUE_NULL _FME_BLANK_STRING_;CASE_SENSITIVE_TEST CRS ATTRIBUTE_IS_MISSING _FME_BLANK_STRING_'@Value(Details.CRS)'FME_NUM_CONDITIONS2___
    -> keepOutputAttributes_3
keepOutputAttributes_3: AttributeKeeper
    CREATE_BULK_MODE_FEATURES = NO
    KEEP_ATTRS = CRS,dataSource,Description,STANOX,TIPLOC,fme_color
    -> joinTiploc_5 [LEFT]
    -> DuplicateFilter_8
joinTiploc_5: FeatureJoiner
    ATTR_CONFLICT_RES = Use Left
    GEOMETRY_HANDLING = Use Left
    JOIN_KEYS = TIPLOC TIPLOC STRING
    JOIN_MODE = Inner
    JOINED -> keepOutputAttributes_4
    UNJOINED_LEFT -> keepOutputAttributes_4
    UNJOINED_RIGHT -> keepOutputAttributes_4
    <REJECTED> -> keepOutputAttributes_4
keepOutputAttributes_4: AttributeKeeper
    CREATE_BULK_MODE_FEATURES = NO
    KEEP_ATTRS = CRS,dataSource,Description,STANOX,TIPLOC,fme_color
    -> joinTiploc_6 [LEFT]
    -> DuplicateFilter_7
DuplicateFilter_7 [off]
    INPUT_ORDERED_CHOICE = No
    KEYATTR = TIPLOC
joinTiploc_6: FeatureJoiner
    ATTR_CONFLICT_RES = Use Left
    GEOMETRY_HANDLING = Use Left
    JOIN_KEYS = TIPLOC TIPLOC STRING
    JOIN_MODE = Inner
    JOINED -> keepOutputAttributes_5
    UNJOINED_LEFT -> keepOutputAttributes_5
    UNJOINED_RIGHT -> keepOutputAttributes_5
    <REJECTED> -> keepOutputAttributes_5
keepOutputAttributes_5: AttributeKeeper
    CREATE_BULK_MODE_FEATURES = NO
    KEEP_ATTRS = CRS,dataSource,Description,STANOX,TIPLOC,fme_color
    -> joinTiploc_7 [LEFT]
    -> DuplicateFilter_6
DuplicateFilter_6 [off]
    INPUT_ORDERED_CHOICE = No
    KEYATTR = TIPLOC
joinTiploc_7: FeatureJoiner
    ATTR_CONFLICT_RES = Use Left
    GEOMETRY_HANDLING = Use Left
    JOIN_KEYS = TIPLOC TIPLOC STRING
    JOIN_MODE = Inner
    JOINED -> AttributeCreator_13
    UNJOINED_LEFT -> keepOutputAttributes_6
    UNJOINED_RIGHT -> keepOutputAttributes_6
    <REJECTED> -> keepOutputAttributes_6
AttributeCreator_13
    ATTR_TABLE:
      SET_TO STANOX = FME_CONDITIONAL:DEFAULT_VALUE'@Value(STANOX)'BOOL_OP;OR;COMPOSITE_TEST;1 OR 2 OR 3;CASE_SENSITIVE_TEST STANOX ATTRIBUTE_IS_EMPTY _FME_BLANK_STRING_;CASE_SENSITIVE_TEST STANOX ATTRIBUTE_VALUE_NULL _FME_BLANK_STRING_;CASE_SENSITIVE_TEST STANOX ATTRIBUTE_IS_MISSING _FME_BLANK_STRING_'@Value(StanoxCode)'FME_NUM_CONDITIONS2___
      SET_TO TIPLOC = FME_CONDITIONAL:DEFAULT_VALUE'@Value(TIPLOC)'BOOL_OP;OR;COMPOSITE_TEST;1 OR 2 OR 3;CASE_SENSITIVE_TEST TIPLOC ATTRIBUTE_IS_EMPTY _FME_BLANK_STRING_;CASE_SENSITIVE_TEST TIPLOC ATTRIBUTE_VALUE_NULL _FME_BLANK_STRING_;CASE_SENSITIVE_TEST TIPLOC ATTRIBUTE_IS_MISSING _FME_BLANK_STRING_'@Value(LocationCode)'FME_NUM_CONDITIONS2___
      SET_TO Description = FME_CONDITIONAL:DEFAULT_VALUE'@Value(Description)'BOOL_OP;OR;COMPOSITE_TEST;1 OR 2 OR 3;CASE_SENSITIVE_TEST Description ATTRIBUTE_IS_EMPTY _FME_BLANK_STRING_;CASE_SENSITIVE_TEST Description ATTRIBUTE_VALUE_NULL _FME_BLANK_STRING_;CASE_SENSITIVE_TEST Description ATTRIBUTE_IS_MISSING _FME_BLANK_STRING_'@Value(LocationName)'FME_NUM_CONDITIONS2___
    -> keepOutputAttributes_6
keepOutputAttributes_6: AttributeKeeper
    CREATE_BULK_MODE_FEATURES = NO
    KEEP_ATTRS = CRS,dataSource,Description,STANOX,TIPLOC,fme_color
    -> joinTiploc_9 [LEFT]
joinTiploc_9: FeatureJoiner
    ATTR_CONFLICT_RES = Use Left
    GEOMETRY_HANDLING = Use Left
    JOIN_KEYS = TIPLOC TIPLOC STRING
    JOIN_MODE = Inner
    JOINED -> AttributeCreator_14
    UNJOINED_LEFT -> joinStanox_3 [LEFT]
    UNJOINED_RIGHT -> joinStanox_3 [RIGHT]
    <REJECTED> -> joinStanox_3 [LEFT]
AttributeCreator_14
    ATTR_TABLE:
      SET_TO STANOX = FME_CONDITIONAL:DEFAULT_VALUE'@Value(STANOX)'BOOL_OP;OR;COMPOSITE_TEST;1 OR 2 OR 3;CASE_SENSITIVE_TEST STANOX ATTRIBUTE_IS_EMPTY _FME_BLANK_STRING_;CASE_SENSITIVE_TEST STANOX ATTRIBUTE_VALUE_NULL _FME_BLANK_STRING_;CASE_SENSITIVE_TEST STANOX ATTRIBUTE_IS_MISSING _FME_BLANK_STRING_'@Value(TIPLOCDATA.STANOX)'FME_NUM_CONDITIONS2___
      SET_TO TIPLOC = FME_CONDITIONAL:DEFAULT_VALUE'@Value(TIPLOC)'BOOL_OP;OR;COMPOSITE_TEST;1 OR 2 OR 3;CASE_SENSITIVE_TEST TIPLOC ATTRIBUTE_IS_EMPTY _FME_BLANK_STRING_;CASE_SENSITIVE_TEST TIPLOC ATTRIBUTE_VALUE_NULL _FME_BLANK_STRING_;CASE_SENSITIVE_TEST TIPLOC ATTRIBUTE_IS_MISSING _FME_BLANK_STRING_'@Value(TIPLOCDATA.TIPLOC)'FME_NUM_CONDITIONS2___
      SET_TO Description = FME_CONDITIONAL:DEFAULT_VALUE'@Value(Description)'BOOL_OP;OR;COMPOSITE_TEST;1 OR 2 OR 3;CASE_SENSITIVE_TEST Description ATTRIBUTE_IS_EMPTY _FME_BLANK_STRING_;CASE_SENSITIVE_TEST Description ATTRIBUTE_VALUE_NULL _FME_BLANK_STRING_;CASE_SENSITIVE_TEST Description ATTRIBUTE_IS_MISSING _FME_BLANK_STRING_'@Value(TIPLOCDATA.NLCDESC)'FME_NUM_CONDITIONS2___
      SET_TO CRS = FME_CONDITIONAL:DEFAULT_VALUE'@Value(CRS)'BOOL_OP;OR;COMPOSITE_TEST;1 OR 2 OR 3;CASE_SENSITIVE_TEST CRS ATTRIBUTE_IS_EMPTY _FME_BLANK_STRING_;CASE_SENSITIVE_TEST CRS ATTRIBUTE_VALUE_NULL _FME_BLANK_STRING_;CASE_SENSITIVE_TEST CRS ATTRIBUTE_IS_MISSING _FME_BLANK_STRING_'@Value(TIPLOCDATA.3ALPHA)'FME_NUM_CONDITIONS2___
    -> keepOutputAttributes_8
joinStanox_3: FeatureJoiner
    ATTR_CONFLICT_RES = Use Left
    GEOMETRY_HANDLING = Use Left
    JOIN_KEYS = STANOX STANOX AUTO
    JOIN_MODE = Inner
    JOINED -> AttributeCreator_9
    UNJOINED_LEFT -> keepOutputAttributes_8
    UNJOINED_RIGHT -> keepOutputAttributes_8
    <REJECTED> -> keepOutputAttributes_8
AttributeCreator_9
    ATTR_TABLE:
      SET_TO STANOX = FME_CONDITIONAL:DEFAULT_VALUE'@Value(STANOX)'BOOL_OP;OR;COMPOSITE_TEST;1 OR 2 OR 3;CASE_SENSITIVE_TEST STANOX ATTRIBUTE_IS_EMPTY _FME_BLANK_STRING_;CASE_SENSITIVE_TEST STANOX ATTRIBUTE_VALUE_NULL _FME_BLANK_STRING_;CASE_SENSITIVE_TEST STANOX ATTRIBUTE_IS_MISSING _FME_BLANK_STRING_'@Value(TIPLOCDATA.STANOX)'FME_NUM_CONDITIONS2___
      SET_TO Description = FME_CONDITIONAL:DEFAULT_VALUE'@Value(Description)'BOOL_OP;OR;COMPOSITE_TEST;1 OR 2 OR 3;CASE_SENSITIVE_TEST Description ATTRIBUTE_IS_EMPTY _FME_BLANK_STRING_;CASE_SENSITIVE_TEST Description ATTRIBUTE_VALUE_NULL _FME_BLANK_STRING_;CASE_SENSITIVE_TEST Description ATTRIBUTE_IS_MISSING _FME_BLANK_STRING_'@Value(TIPLOCDATA.NLCDESC)'FME_NUM_CONDITIONS2___
      SET_TO CRS = FME_CONDITIONAL:DEFAULT_VALUE'@Value(CRS)'BOOL_OP;OR;COMPOSITE_TEST;1 OR 2 OR 3;CASE_SENSITIVE_TEST CRS ATTRIBUTE_IS_EMPTY _FME_BLANK_STRING_;CASE_SENSITIVE_TEST CRS ATTRIBUTE_VALUE_NULL _FME_BLANK_STRING_;CASE_SENSITIVE_TEST CRS ATTRIBUTE_IS_MISSING _FME_BLANK_STRING_'@Value(TIPLOCDATA.3ALPHA)'FME_NUM_CONDITIONS2___
      SET_TO TIPLOC = FME_CONDITIONAL:DEFAULT_VALUE'@Value(TIPLOC)'BOOL_OP;OR;COMPOSITE_TEST;1 OR 2 OR 3;CASE_SENSITIVE_TEST TIPLOC ATTRIBUTE_IS_EMPTY _FME_BLANK_STRING_;CASE_SENSITIVE_TEST TIPLOC ATTRIBUTE_VALUE_NULL _FME_BLANK_STRING_;CASE_SENSITIVE_TEST TIPLOC ATTRIBUTE_IS_MISSING _FME_BLANK_STRING_'@Value(TIPLOCDATA.TIPLOC)'FME_NUM_CONDITIONS2___
    -> keepOutputAttributes_8
keepOutputAttributes_8: AttributeKeeper
    CREATE_BULK_MODE_FEATURES = NO
    KEEP_ATTRS = CRS,dataSource,Description,STANOX,TIPLOC,fme_color
    -> CoordinateExtractor
    -> DuplicateFilter_10

Bookmark: New Bookmark
AttributeRemover_3
    -> AttributeKeeper_3
    -> FeatureJoiner_3 [LEFT]
AttributeRemover_2
    REMOVE_ATTRS = fme_fill_color,EASTING,NORTHING
    -> AttributeKeeper_3
    -> FeatureJoiner_3 [RIGHT]
FeatureJoiner_3
    ATTR_CONFLICT_RES = Use Left
    GEOMETRY_HANDLING = Aggregate Left and Right (Enforce Unique Names)
    JOIN_KEYS = TIPLOC TIPLOC STRING
    JOIN_MODE = Inner
    JOINED -> VertexExtractor_2
    <REJECTED> -> Inspector_3
VertexExtractor_2
    Point -> LineBuilder_2
LineBuilder_2
    ACCUM_INPUT_ATTRS = Use Attributes From One Feature
    GROUP_BY = TIPLOC
    REMOVE_DUPLICATES = No
    LINE -> reprojectNG_2
    <REJECTED> -> Inspector_3
reprojectNG_2: Reprojector
    DEST = EPSG:27700
    INTERPOLATION_TYPE_NAME = Nearest Neighbor
    RASTER_CELL_SIZE = Preserve Cells
    RASTER_TOLERANCE = 0.0
    REPROJECTED -> LengthCalculator_2
LengthCalculator_2
    DIM = 2
    LEN_ATTR = _lengthGB
    MULT = 1
    -> Sorter_3
    -> AttributeKeeper_9
Sorter_3
    SORT_PARM = _lengthGB NUMERIC DESCENDING
    SORTED -> AttributeKeeper_4
AttributeKeeper_4
    CREATE_BULK_MODE_FEATURES = NO
    KEEP_ATTRS = _length,Description,DisplayName,TIPLOC
    -> reprojector_LL_2
reprojector_LL_2: Reprojector
    DEST = LL-WGS84
    INTERPOLATION_TYPE_NAME = Nearest Neighbor
    RASTER_CELL_SIZE = Preserve Cells
    RASTER_TOLERANCE = 0.0
    REPROJECTED -> Inspector_4
Inspector_3 [off]
AttributeKeeper_3
    CREATE_BULK_MODE_FEATURES = NO
    KEEP_ATTRS = dataSource,TIPLOC,fme_color
    -> Inspector_4
Inspector_4

Bookmark: New Bookmark
FeatureJoiner_2
    ATTR_CONFLICT_RES = Use Left
    GEOMETRY_HANDLING = Aggregate Left and Right (Enforce Unique Names)
    JOIN_KEYS = TIPLOC TIPLOC STRING
    JOIN_MODE = Inner
    JOINED -> VertexExtractor
    <REJECTED> -> Inspector
VertexExtractor
    Point -> LineBuilder
LineBuilder
    ACCUM_INPUT_ATTRS = Use Attributes From One Feature
    GROUP_BY = TIPLOC
    REMOVE_DUPLICATES = No
    LINE -> reprojectNG
    <REJECTED> -> Inspector
reprojectNG: Reprojector
    DEST = EPSG:27700
    INTERPOLATION_TYPE_NAME = Nearest Neighbor
    RASTER_CELL_SIZE = Preserve Cells
    RASTER_TOLERANCE = 0.0
    REPROJECTED -> LengthCalculator
LengthCalculator
    DIM = 2
    LEN_ATTR = _lengthGR
    MULT = 1
    -> Sorter_2
    -> AttributeKeeper_7
Sorter_2
    SORT_PARM = _lengthGR NUMERIC DESCENDING
    SORTED -> AttributeKeeper_2
AttributeKeeper_2
    CREATE_BULK_MODE_FEATURES = NO
    KEEP_ATTRS = _length,Description,DisplayName,TIPLOC
    -> reprojector_LL
reprojector_LL: Reprojector
    DEST = LL-WGS84
    INTERPOLATION_TYPE_NAME = Nearest Neighbor
    RASTER_CELL_SIZE = Preserve Cells
    RASTER_TOLERANCE = 0.0
    REPROJECTED -> Inspector_2
Inspector [off]
AttributeKeeper
    CREATE_BULK_MODE_FEATURES = NO
    KEEP_ATTRS = Description,DisplayName,dataSource,TIPLOC,fme_color
    -> Inspector_2
Inspector_2

Bookmark: findClosestPair
AttributeKeeper_7
    CREATE_BULK_MODE_FEATURES = NO
    KEEP_ATTRS = dataSource,fme_color,_lengthGR,TIPLOC
    -> FeatureJoiner_5 [LEFT]
AttributeKeeper_9
    CREATE_BULK_MODE_FEATURES = NO
    KEEP_ATTRS = _lengthGB,dataSource,fme_color,TIPLOC
    -> FeatureJoiner_5 [RIGHT]
FeatureJoiner_5
    ATTR_CONFLICT_RES = Use Left
    GEOMETRY_HANDLING = Aggregate Left and Right (Enforce Unique Names)
    JOIN_KEYS = TIPLOC TIPLOC STRING
    JOIN_MODE = Inner
    JOINED -> FeatureJoiner_6 [LEFT]
AttributeKeeper_8
    CREATE_BULK_MODE_FEATURES = NO
    KEEP_ATTRS = dataSource,fme_color,TIPLOC,_lengthRB
    -> FeatureJoiner_6 [RIGHT]
FeatureJoiner_6
    ATTR_CONFLICT_RES = Use Left
    GEOMETRY_HANDLING = Aggregate Left and Right (Enforce Unique Names)
    JOIN_KEYS = TIPLOC TIPLOC STRING
    JOIN_MODE = Inner
    JOINED -> evaluateMinMax
evaluateMinMax: AttributeCreator
    ATTR_TABLE:
      SET_TO minDiff = @Evaluate(@min(@Value(_lengthGB),@Value(_lengthGR),@Value(_lengthRB)))
      SET_TO maxDiff = @Evaluate(@max(@Value(_lengthGB),@Value(_lengthGR),@Value(_lengthRB)))
    -> TestFilter_3
TestFilter_3
    DEFAULT_VALUE = <UNFILTERED>
    TEST_LIST = "BOOL_OP,OR,COMPOSITE_TEST,""""""1"""""",TEST_CLAUSE,NUM_TEST @Value(minDiff) > 1000",diff_greater_1km,"BOOL_OP,OR,COMPOSITE_TEST,""""""1"""""",TEST_CLAUSE,NUM_TEST @Value(maxDiff) <= 100",max diff less than 100m
    diff_greater_1km -> GeometryRemover_5
    diff_greater_1km -> reproject_LL
    max diff less than 100m -> GeometryRemover_5
    <UNFILTERED> -> GeometryRemover_5
GeometryRemover_5
    -> AttributeKeeper_13
AttributeKeeper_13
    CREATE_BULK_MODE_FEATURES = NO
    KEEP_ATTRS = _lengthGB,_lengthGR,_lengthRB,minDiff,TIPLOC
    -> TestFilter_2
TestFilter_2
    DEFAULT_VALUE = <UNFILTERED>
    TEST_LIST = "BOOL_OP,OR,COMPOSITE_TEST,""""""1"""""",TEST_CLAUSE,NUM_TEST @Value(_lengthGB) = @Value(minDiff)",RED BAD,"BOOL_OP,OR,COMPOSITE_TEST,""""""1"""""",TEST_CLAUSE,NUM_TEST @Value(_lengthGR) = @Value(minDiff)",BLUE BAD,"BOOL_OP,OR,COMPOSITE_TEST,""""""1"""""",TEST_CLAUSE,NUM_TEST @Value(_lengthRB) = @Value(minDiff)",GREEN BAD
    RED BAD -> AttributeKeeper_16
    BLUE BAD -> AttributeKeeper_15
    GREEN BAD -> AttributeKeeper_14
AttributeKeeper_16
    CREATE_BULK_MODE_FEATURES = NO
    KEEP_ATTRS = TIPLOC
    -> FeatureJoiner_8 [RIGHT]
AttributeKeeper_15
    CREATE_BULK_MODE_FEATURES = NO
    KEEP_ATTRS = TIPLOC
    -> FeatureJoiner_9 [RIGHT]
AttributeKeeper_14
    CREATE_BULK_MODE_FEATURES = NO
    KEEP_ATTRS = TIPLOC
    -> FeatureJoiner_7 [RIGHT]
reproject_LL: Reprojector
    DEST = LL-WGS84
    INTERPOLATION_TYPE_NAME = Nearest Neighbor
    RASTER_CELL_SIZE = Preserve Cells
    RASTER_TOLERANCE = 0.0
    REPROJECTED -> Inspector_7
Inspector_7

Bookmark: New Bookmark
AttributeRemover_5
    REMOVE_ATTRS = Codes,Details.BPlan_TimingPoint,Details.CRS,Details.CompulsoryStop,Details.ForceLPB,Details.Nalco,Details.OffNetwork,Details.TPS_StationCategory,Details.TPS_StationType,Details.UIC,Details.Zone,Elevation.Google,Elevation.OpenElevation,Elevation.OrdnanceSurvey5,Elevation.OrdnanceSurvey50,InBPlan,InTPS,Latitude,Longitude,NodeId,Stanox,_element_index,fme_fill_color
    -> AttributeKeeper_5
    -> FeatureJoiner_4 [LEFT]
AttributeRemover_4
    REMOVE_ATTRS = fme_fill_color,EASTING,NORTHING
    -> AttributeKeeper_5
    -> FeatureJoiner_4 [RIGHT]
FeatureJoiner_4
    ATTR_CONFLICT_RES = Use Left
    GEOMETRY_HANDLING = Aggregate Left and Right (Enforce Unique Names)
    JOIN_KEYS = TIPLOC TIPLOC STRING
    JOIN_MODE = Inner
    JOINED -> VertexExtractor_3
    <REJECTED> -> Inspector_5
VertexExtractor_3
    Point -> LineBuilder_3
LineBuilder_3
    ACCUM_INPUT_ATTRS = Use Attributes From One Feature
    GROUP_BY = TIPLOC
    REMOVE_DUPLICATES = No
    LINE -> reprojectNG_3
    <REJECTED> -> Inspector_5
reprojectNG_3: Reprojector
    DEST = EPSG:27700
    INTERPOLATION_TYPE_NAME = Nearest Neighbor
    RASTER_CELL_SIZE = Preserve Cells
    RASTER_TOLERANCE = 0.0
    REPROJECTED -> LengthCalculator_3
LengthCalculator_3
    DIM = 2
    LEN_ATTR = _lengthRB
    MULT = 1
    -> Sorter_4
    -> AttributeKeeper_8
Sorter_4
    SORT_PARM = _lengthRB NUMERIC DESCENDING
    SORTED -> AttributeKeeper_6
AttributeKeeper_6
    CREATE_BULK_MODE_FEATURES = NO
    KEEP_ATTRS = _length,Description,DisplayName,TIPLOC
    -> reprojector_LL_3
reprojector_LL_3: Reprojector
    DEST = LL-WGS84
    INTERPOLATION_TYPE_NAME = Nearest Neighbor
    RASTER_CELL_SIZE = Preserve Cells
    RASTER_TOLERANCE = 0.0
    REPROJECTED -> Inspector_6
Inspector_5 [off]
AttributeKeeper_5
    CREATE_BULK_MODE_FEATURES = NO
    KEEP_ATTRS = Description,DisplayName,dataSource,TIPLOC,fme_color,EASTING,NORTHING
    -> Inspector_6
Inspector_6

Bookmark: G
Junction_6
    -> FeatureJoiner_11 [LEFT]
    -> FeatureJoiner_26 [LEFT]

Bookmark: R
Junction_7
    -> FeatureJoiner_11 [RIGHT]
    -> FeatureJoiner_25 [LEFT]

Bookmark: split into two sets
FeatureJoiner_11
    ATTR_CONFLICT_RES = Use Left
    GEOMETRY_HANDLING = Aggregate Left and Right (Enforce Unique Names)
    JOIN_KEYS = TIPLOC TIPLOC STRING
    JOIN_MODE = Inner
    JOINED -> FeatureJoiner_13 [LEFT]
    JOINED -> Junction_13
    UNJOINED_LEFT -> FeatureJoiner_12 [LEFT]
    UNJOINED_RIGHT -> FeatureJoiner_12 [LEFT]
    <REJECTED> -> rejected
rejected: Inspector [off]
FeatureJoiner_12
    ATTR_CONFLICT_RES = Use Left
    GEOMETRY_HANDLING = Aggregate Left and Right (Enforce Unique Names)
    JOIN_KEYS = TIPLOC TIPLOC STRING
    JOIN_MODE = Inner
    JOINED -> Junction_14
    UNJOINED_LEFT -> in_one_set
    UNJOINED_RIGHT -> in_one_set
AttributeRemover_12
    REMOVE_ATTRS = STANOX,STANOXwp,Stanox,fme_fill_color,fme_rejection_message,fme_rejection_code,CRS,Details.CRS
    -> DuplicateFilter_4
    -> Junction_2
DuplicateFilter_4
    INPUT_ORDERED_CHOICE = No
    KEYATTR = TIPLOC
    UNIQUE -> VertexExtractor_5
VertexExtractor_5
    Point -> AttributeKeeper_28
AttributeKeeper_28
    CREATE_BULK_MODE_FEATURES = NO
    KEEP_ATTRS = _part_number,dataSource,Description,TIPLOC
    -> splitPartNumber
splitPartNumber: TestFilter
    DEFAULT_VALUE = <UNFILTERED>
    TEST_LIST = "BOOL_OP,OR,COMPOSITE_TEST,""""""1"""""",TEST_CLAUSE,NUM_TEST @Value(_part_number) = 0",0
    0 -> AttributeRemover_17
    <UNFILTERED> -> AttributeRemover_18
AttributeRemover_17
    REMOVE_ATTRS = _part_number
    -> Junction_15
AttributeRemover_18
    REMOVE_ATTRS = _part_number
    -> Junction_5
in_one_set: Inspector
FeatureJoiner_13
    ATTR_CONFLICT_RES = Use Left
    GEOMETRY_HANDLING = Aggregate Left and Right (Enforce Unique Names)
    JOIN_KEYS = TIPLOC TIPLOC STRING
    JOIN_MODE = Inner
    JOINED -> in_all_sets
in_all_sets: Inspector

Bookmark: R+G
Junction_13
    -> AttributeRemover_12

Bookmark: B
Junction_8
    -> FeatureJoiner_12 [RIGHT]
    -> FeatureJoiner_13 [RIGHT]
    -> FeatureJoiner_24 [LEFT]

Bookmark: B + (R|G)
Junction_14
    -> AttributeRemover_12

Bookmark: New Bookmark
AttributeRemover_14
    REMOVE_ATTRS = Codes,Details.BPlan_TimingPoint,Details.CRS,Details.CompulsoryStop,Details.ForceLPB,Details.Nalco,Details.OffNetwork,Details.TPS_StationCategory,Details.TPS_StationType,Details.UIC,Details.Zone,Elevation.Google,Elevation.OpenElevation,Elevation.OrdnanceSurvey5,Elevation.OrdnanceSurvey50,InBPlan,InTPS,Latitude,Longitude,NodeId,Stanox,_element_index,fme_fill_color
    -> AttributeKeeper_17
    -> FeatureJoiner_14 [LEFT]
AttributeRemover_13
    REMOVE_ATTRS = fme_fill_color,EASTING,NORTHING
    -> AttributeKeeper_17
    -> FeatureJoiner_14 [RIGHT]
FeatureJoiner_14
    ATTR_CONFLICT_RES = Use Left
    GEOMETRY_HANDLING = Aggregate Left and Right (Enforce Unique Names)
    JOIN_KEYS = TIPLOC TIPLOC STRING
    JOIN_MODE = Inner
    JOINED -> VertexExtractor_6
    <REJECTED> -> Inspector_11
VertexExtractor_6
    Point -> LineBuilder_5
LineBuilder_5
    ACCUM_INPUT_ATTRS = Use Attributes From One Feature
    GROUP_BY = TIPLOC
    REMOVE_DUPLICATES = No
    LINE -> reprojectNG_5
    <REJECTED> -> Inspector_11
reprojectNG_5: Reprojector
    DEST = EPSG:27700
    INTERPOLATION_TYPE_NAME = Nearest Neighbor
    RASTER_CELL_SIZE = Preserve Cells
    RASTER_TOLERANCE = 0.0
    REPROJECTED -> LengthCalculator_5
LengthCalculator_5
    DIM = 2
    LEN_ATTR = _lengthRB
    MULT = 1
    -> Sorter_6
    -> AttributeKeeper_RB
Sorter_6
    SORT_PARM = _lengthRB NUMERIC DESCENDING
    SORTED -> AttributeKeeper_18
AttributeKeeper_18
    CREATE_BULK_MODE_FEATURES = NO
    KEEP_ATTRS = _length,Description,DisplayName,TIPLOC
    -> reprojector_LL_5
reprojector_LL_5: Reprojector
    DEST = LL-WGS84
    INTERPOLATION_TYPE_NAME = Nearest Neighbor
    RASTER_CELL_SIZE = Preserve Cells
    RASTER_TOLERANCE = 0.0
    REPROJECTED -> Inspector_12
Inspector_11 [off]
AttributeKeeper_17
    CREATE_BULK_MODE_FEATURES = NO
    KEEP_ATTRS = Description,DisplayName,dataSource,TIPLOC,fme_color,EASTING,NORTHING
    -> Inspector_12
Inspector_12

Bookmark: New Bookmark
AttributeRemover_16
    REMOVE_ATTRS = Codes,Details.BPlan_TimingPoint,Details.CRS,Details.CompulsoryStop,Details.ForceLPB,Details.Nalco,Details.OffNetwork,Details.TPS_StationCategory,Details.TPS_StationType,Details.UIC,Details.Zone,Elevation.Google,Elevation.OpenElevation,Elevation.OrdnanceSurvey5,Elevation.OrdnanceSurvey50,InBPlan,InTPS,Latitude,Longitude,NodeId,Stanox,_element_index,fme_fill_color
    -> AttributeKeeper_19
    -> FeatureJoiner_15 [LEFT]
AttributeRemover_15
    REMOVE_ATTRS = fme_fill_color,EASTING,NORTHING
    -> AttributeKeeper_19
    -> FeatureJoiner_15 [RIGHT]
FeatureJoiner_15
    ATTR_CONFLICT_RES = Use Left
    GEOMETRY_HANDLING = Aggregate Left and Right (Enforce Unique Names)
    JOIN_KEYS = TIPLOC TIPLOC STRING
    JOIN_MODE = Inner
    JOINED -> VertexExtractor_7
    <REJECTED> -> Inspector_13
VertexExtractor_7
    Point -> LineBuilder_6
LineBuilder_6
    ACCUM_INPUT_ATTRS = Use Attributes From One Feature
    GROUP_BY = TIPLOC
    REMOVE_DUPLICATES = No
    LINE -> reprojectNG_6
    <REJECTED> -> Inspector_13
reprojectNG_6: Reprojector
    DEST = EPSG:27700
    INTERPOLATION_TYPE_NAME = Nearest Neighbor
    RASTER_CELL_SIZE = Preserve Cells
    RASTER_TOLERANCE = 0.0
    REPROJECTED -> LengthCalculator_6
LengthCalculator_6
    DIM = 2
    LEN_ATTR = _lengthBY
    MULT = 1
    -> Sorter_7
    -> AttributeKeeper_BY
Sorter_7
    SORT_PARM = _lengthBY NUMERIC DESCENDING
    SORTED -> AttributeKeeper_20
AttributeKeeper_20
    CREATE_BULK_MODE_FEATURES = NO
    KEEP_ATTRS = _length,Description,DisplayName,TIPLOC
    -> reprojector_LL_6
reprojector_LL_6: Reprojector
    DEST = LL-WGS84
    INTERPOLATION_TYPE_NAME = Nearest Neighbor
    RASTER_CELL_SIZE = Preserve Cells
    RASTER_TOLERANCE = 0.0
    REPROJECTED -> Inspector_14
Inspector_13 [off]
AttributeKeeper_19
    CREATE_BULK_MODE_FEATURES = NO
    KEEP_ATTRS = Description,DisplayName,dataSource,TIPLOC,fme_color,EASTING,NORTHING
    -> Inspector_14
Inspector_14

Bookmark: findClosestPair
AttributeKeeper_RB
    CREATE_BULK_MODE_FEATURES = NO
    KEEP_ATTRS = dataSource,Description,TIPLOC,_lengthRB
    -> FeatureJoiner_16 [LEFT]
    -> FeatureJoiner_27 [LEFT]
AttributeKeeper_BY
    CREATE_BULK_MODE_FEATURES = NO
    KEEP_ATTRS = dataSource,Description,fme_color,TIPLOC,_lengthBY
    -> FeatureJoiner_16 [RIGHT]
    -> FeatureJoiner_20 [LEFT]
FeatureJoiner_16
    ATTR_CONFLICT_RES = Use Left
    GEOMETRY_HANDLING = Aggregate Left and Right (Enforce Unique Names)
    JOIN_KEYS = TIPLOC TIPLOC STRING
    JOIN_MODE = Inner
    JOINED -> FeatureJoiner_17 [LEFT]
AttributeKeeper_RY
    CREATE_BULK_MODE_FEATURES = NO
    KEEP_ATTRS = Description,dataSource,fme_color,TIPLOC,_lengthRY
    -> FeatureJoiner_17 [RIGHT]
    -> FeatureJoiner_19 [RIGHT]
FeatureJoiner_17
    ATTR_CONFLICT_RES = Use Left
    GEOMETRY_HANDLING = Aggregate Left and Right (Enforce Unique Names)
    JOIN_KEYS = TIPLOC TIPLOC STRING
    JOIN_MODE = Inner
    JOINED -> evaluateMinMax_2
evaluateMinMax_2: AttributeCreator
    ATTR_TABLE:
      SET_TO minDiff = @Evaluate(@min(@Value(_lengthBY),@Value(_lengthRY),@Value(_lengthRB)))
      SET_TO maxDiff = @Evaluate(@max(@Value(_lengthBY),@Value(_lengthRY),@Value(_lengthRB)))
    -> TestFilter_5
TestFilter_5
    DEFAULT_VALUE = <UNFILTERED>
    TEST_LIST = "BOOL_OP,OR,COMPOSITE_TEST,""""""1"""""",TEST_CLAUSE,NUM_TEST @Value(minDiff) > 1000",diff_greater_1km,"BOOL_OP,OR,COMPOSITE_TEST,""""""1"""""",TEST_CLAUSE,NUM_TEST @Value(maxDiff) <= 100",max diff less than 100m
    diff_greater_1km -> GeometryRemover_2
    diff_greater_1km -> reproject_LL_2
    max diff less than 100m -> GeometryRemover_2
    <UNFILTERED> -> GeometryRemover_2
GeometryRemover_2
    -> AttributeKeeper_24
AttributeKeeper_24
    CREATE_BULK_MODE_FEATURES = NO
    KEEP_ATTRS = _lengthRB,minDiff,TIPLOC,_lengthBY,_lengthRY
    -> TestFilter_4
TestFilter_4
    DEFAULT_VALUE = <UNFILTERED>
    TEST_LIST = "BOOL_OP,OR,COMPOSITE_TEST,""""""1"""""",TEST_CLAUSE,NUM_TEST @Value(_lengthBY) = @Value(minDiff)",BY good,"BOOL_OP,OR,COMPOSITE_TEST,""""""1"""""",TEST_CLAUSE,NUM_TEST @Value(_lengthRB) = @Value(minDiff)",RB good,"BOOL_OP,OR,COMPOSITE_TEST,""""""1"""""",TEST_CLAUSE,NUM_TEST @Value(_lengthRY) = @Value(minDiff)",RY good
    BY good -> AttributeKeeper_27
    RB good -> AttributeKeeper_26
    RY good -> AttributeKeeper_25
AttributeKeeper_27
    CREATE_BULK_MODE_FEATURES = NO
    KEEP_ATTRS = TIPLOC
    -> FeatureJoiner_20 [RIGHT]
FeatureJoiner_20
    ATTR_CONFLICT_RES = Use Left
    GEOMETRY_HANDLING = Use Left
    JOIN_KEYS = TIPLOC TIPLOC STRING
    JOIN_MODE = Inner
    JOINED -> VertexExtractor_8
AttributeKeeper_26
    CREATE_BULK_MODE_FEATURES = NO
    KEEP_ATTRS = TIPLOC
    -> FeatureJoiner_18 [RIGHT]
    -> FeatureJoiner_27 [RIGHT]
FeatureJoiner_27
    ATTR_CONFLICT_RES = Use Left
    GEOMETRY_HANDLING = Use Left
    JOIN_KEYS = TIPLOC TIPLOC STRING
    JOIN_MODE = Inner
    JOINED -> VertexExtractor_8
AttributeKeeper_25
    CREATE_BULK_MODE_FEATURES = NO
    KEEP_ATTRS = TIPLOC
    -> FeatureJoiner_19 [LEFT]
FeatureJoiner_19
    ATTR_CONFLICT_RES = Use Right
    GEOMETRY_HANDLING = Use Right
    JOIN_KEYS = TIPLOC TIPLOC STRING
    JOIN_MODE = Inner
    JOINED -> VertexExtractor_8
VertexExtractor_8
    Point -> DuplicateFilter_5
reproject_LL_2: Reprojector
    DEST = LL-WGS84
    INTERPOLATION_TYPE_NAME = Nearest Neighbor
    RASTER_CELL_SIZE = Preserve Cells
    RASTER_TOLERANCE = 0.0
    REPROJECTED -> Inspector_15
Inspector_15

Bookmark: New Bookmark
AttributeRemover_7
    REMOVE_ATTRS = Codes,Details.BPlan_TimingPoint,Details.CRS,Details.CompulsoryStop,Details.ForceLPB,Details.Nalco,Details.OffNetwork,Details.TPS_StationCategory,Details.TPS_StationType,Details.UIC,Details.Zone,Elevation.Google,Elevation.OpenElevation,Elevation.OrdnanceSurvey5,Elevation.OrdnanceSurvey50,InBPlan,InTPS,Latitude,Longitude,NodeId,Stanox,_element_index,fme_fill_color
    -> AttributeKeeper_11
    -> FeatureJoiner_10 [LEFT]
AttributeRemover_6
    REMOVE_ATTRS = fme_fill_color,EASTING,NORTHING
    -> AttributeKeeper_11
    -> FeatureJoiner_10 [RIGHT]
FeatureJoiner_10
    ATTR_CONFLICT_RES = Use Left
    GEOMETRY_HANDLING = Aggregate Left and Right (Enforce Unique Names)
    JOIN_KEYS = TIPLOC TIPLOC STRING
    JOIN_MODE = Inner
    JOINED -> VertexExtractor_4
    <REJECTED> -> Inspector_8
VertexExtractor_4
    Point -> LineBuilder_4
LineBuilder_4
    ACCUM_INPUT_ATTRS = Use Attributes From One Feature
    GROUP_BY = TIPLOC
    REMOVE_DUPLICATES = No
    LINE -> reprojectNG_4
    <REJECTED> -> Inspector_8
reprojectNG_4: Reprojector
    DEST = EPSG:27700
    INTERPOLATION_TYPE_NAME = Nearest Neighbor
    RASTER_CELL_SIZE = Preserve Cells
    RASTER_TOLERANCE = 0.0
    REPROJECTED -> LengthCalculator_4
LengthCalculator_4
    DIM = 2
    LEN_ATTR = _lengthRY
    MULT = 1
    -> Sorter_5
    -> AttributeKeeper_RY
Sorter_5
    SORT_PARM = _lengthRY NUMERIC DESCENDING
    SORTED -> AttributeKeeper_12
AttributeKeeper_12
    CREATE_BULK_MODE_FEATURES = NO
    KEEP_ATTRS = _length,Description,DisplayName,TIPLOC
    -> reprojector_LL_4
reprojector_LL_4: Reprojector
    DEST = LL-WGS84
    INTERPOLATION_TYPE_NAME = Nearest Neighbor
    RASTER_CELL_SIZE = Preserve Cells
    RASTER_TOLERANCE = 0.0
    REPROJECTED -> Inspector_9
Inspector_8 [off]
AttributeKeeper_11
    CREATE_BULK_MODE_FEATURES = NO
    KEEP_ATTRS = Description,DisplayName,dataSource,TIPLOC,fme_color,EASTING,NORTHING
    -> Inspector_9
Inspector_9

Bookmark: whichOnesAreWeTesting
FeatureJoiner_26
    ATTR_CONFLICT_RES = Use Left
    GEOMETRY_HANDLING = Use Left
    JOIN_KEYS = TIPLOC TIPLOC STRING
    JOIN_MODE = Inner
    JOINED -> Junction_12
    <REJECTED> -> dumpRejects
FeatureJoiner_25
    ATTR_CONFLICT_RES = Use Left
    GEOMETRY_HANDLING = Use Left
    JOIN_KEYS = TIPLOC TIPLOC STRING
    JOIN_MODE = Inner
    JOINED -> Junction_16
    <REJECTED> -> dumpRejects
FeatureJoiner_24
    ATTR_CONFLICT_RES = Use Left
    GEOMETRY_HANDLING = Use Left
    JOIN_KEYS = TIPLOC TIPLOC STRING
    JOIN_MODE = Inner
    JOINED -> Junction_17
    <REJECTED> -> dumpRejects

Bookmark: G
Junction_12
    -> SpatialFilter_3 [Candidate]

Bookmark: R
Junction_16
    -> SpatialFilter_2 [Candidate]

Bookmark: B
Junction_17
    -> SpatialFilter [Candidate]

Bookmark: whichOnesAreBad
SpatialFilter_3
    AGGREGATE_HANDLING = Yes
    ATTR_ACCUM_MODE = Prefix Filter
    ATTR_PREFIX = match.
    BASE_TYPE = Multiple Filters
    CURVE_BOUNDARY_RULE_PARAM = Default Rule
    PASS_CRITERIA = Pass Against One Filter
    PREDICATES = EQUALS CONTAINS TOUCHES
    USE_BOUNDING_BOX = For Filters Only
    FAILED -> FeatureJoiner_23 [RIGHT]
SpatialFilter_2
    AGGREGATE_HANDLING = Yes
    ATTR_ACCUM_MODE = Prefix Filter
    ATTR_PREFIX = match.
    BASE_TYPE = Multiple Filters
    CURVE_BOUNDARY_RULE_PARAM = Default Rule
    PASS_CRITERIA = Pass Against One Filter
    PREDICATES = EQUALS CONTAINS TOUCHES
    USE_BOUNDING_BOX = For Filters Only
    FAILED -> FeatureJoiner_21 [RIGHT]
SpatialFilter
    AGGREGATE_HANDLING = Yes
    ATTR_ACCUM_MODE = Prefix Filter
    ATTR_PREFIX = match.
    BASE_TYPE = Multiple Filters
    CURVE_BOUNDARY_RULE_PARAM = Default Rule
    PASS_CRITERIA = Pass Against One Filter
    PREDICATES = EQUALS CONTAINS TOUCHES
    USE_BOUNDING_BOX = For Filters Only
    FAILED -> FeatureJoiner_22 [RIGHT]

Bookmark: outputCreation
CoordinateExtractor
    IND = 0
    MODE = Specify Coordinate
    X_ATTR = stop_lon
    Y_ATTR = stop_lat
    -> Reprojector_NG_3
    <REJECTED> -> AttributeRemover
Reprojector_NG_3
    DEST = EPSG:27700
    INTERPOLATION_TYPE_NAME = Nearest Neighbor
    RASTER_CELL_SIZE = Preserve Cells
    RASTER_TOLERANCE = 0.0
    REPROJECTED -> CoordinateExtractor_2
CoordinateExtractor_2
    IND = 0
    MODE = Specify Coordinate
    X_ATTR = easting
    Y_ATTR = northing
    -> AttributeCreator_5
AttributeCreator_5
    ATTR_TABLE:
      SET_TO easting = @Evaluate(@round(@Value(easting),0))
      SET_TO northing = @Evaluate(@round(@Value(northing),0))
    -> Reprojector_LL
Reprojector_LL
    DEST = LL-WGS84
    INTERPOLATION_TYPE_NAME = Nearest Neighbor
    RASTER_CELL_SIZE = Preserve Cells
    RASTER_TOLERANCE = 0.0
    REPROJECTED -> StringReplacer
AttributeRemover
    REMOVE_ATTRS = fme_rejection_code
    -> StringReplacer
StringReplacer
    CASE = NO
    FIND_TEXT = \r|\n
    NO_MATCH = _FME_NO_OP_
    REGEXP = YES
    SRC_ATTRS = CRS,Description,STANOX,TIPLOC
    -> has_STANOX
    -> has_TIPLOC
    -> overallOutputStats
    -> nullCrs
has_TIPLOC: TestFilter
    DEFAULT_VALUE = Ok Id
    TEST_LIST:
      "BOOL_OP,OR,COMPOSITE_TEST,""""""1 OR 2 OR 3"""""",TEST_CLAUSE,TEST TIPLOC ATTRIBUTE_IS_EMPTY ""
      TEST TIPLOC ATTRIBUTE_IS_MISSING ""
      TEST TIPLOC ATTRIBUTE_VALUE_NULL """,NULL id
    Ok Id -> DuplicateFilter
DuplicateFilter
    INPUT_ORDERED_CHOICE = No
    KEYATTR = TIPLOC
    UNIQUE -> AttributeRenamer_7
    UNIQUE -> TiplocOutputStats
    DUPLICATE -> Terminator
TiplocOutputStats: StatisticsCalculator
    CALCULATION_MODE = NUMERIC
    FEAT_STATS = TIPLOC,NUMERIC_MODE,,,COUNT,,,,,,,,,,
    GROUP_BY = dataSource
    SUMMARY -> tiplocOutputStats
tiplocOutputStats: Inspector
AttributeRenamer_7
    ATTR_TABLE:
      RENAME_SET_DEFAULT CRS > stop_code
      RENAME_SET_DEFAULT TIPLOC > stop_id
      RENAME_SET_DEFAULT Description > stop_name
      RENAME_SET_DEFAULT STANOX > platform_code
      RENAME_SET_DEFAULT dataSource > stop_url
    MISSING_INPUT_ATTRS = REMOVE
    -> FeatureWriter [Output]
FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = yes
    CSV2_QUALIFY_FIELD_VALUES = yes
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(outputPath)
    DATASET_ATTR = _dataset
    FEATURE_TYPE_LIST_ATTR = _feature_types
    FORMAT = CSV2
    TOTAL_FEATURES_WRITTEN_ATTR = _total_features_written
    SUMMARY -> inspectorOutputSummary
Terminator
    MESSAGE:
      Translation Terminated:

      Duplicated TIPLOC
has_STANOX: TestFilter
    DEFAULT_VALUE = Ok Id
    TEST_LIST:
      "BOOL_OP,OR,COMPOSITE_TEST,""""""1 OR 2 OR 3"""""",TEST_CLAUSE,TEST STANOX ATTRIBUTE_IS_EMPTY ""
      TEST STANOX ATTRIBUTE_IS_MISSING ""
      TEST STANOX ATTRIBUTE_VALUE_NULL """,NULL id
    NULL id -> Reprojector_NG
    Ok Id -> Sorter_8
    Ok Id -> Reprojector_NG_2
Reprojector_NG
    DEST = EPSG:27700
    INTERPOLATION_TYPE_NAME = Nearest Neighbor
    RASTER_CELL_SIZE = Preserve Cells
    RASTER_TOLERANCE = 0.0
    REPROJECTED -> NeighborFinder15m [BASE]
Reprojector_NG_2
    DEST = EPSG:27700
    INTERPOLATION_TYPE_NAME = Nearest Neighbor
    RASTER_CELL_SIZE = Preserve Cells
    RASTER_TOLERANCE = 0.0
    REPROJECTED -> NeighborFinder15m [CANDIDATE]
NeighborFinder15m
    ATTR_ACCUM_MODE = Prefix Candidate
    CANDIDATES_FIRST = No
    INCOMING_PREFIX = neigh.
    INSERT_VERTEX = No
    K = 1
    MAX = 15
    MEASURES_FROM_CANDIDATE = Yes
    MEASURE_TYPE = Continuous
    MODE = Bases and Candidates
    TREAT_POLYGON_AS = Lines
    MATCHED -> AttributeRenamer_11
    UNMATCHED_BASE -> FeatureWriter_2 [Output]
    <REJECTED> -> dumpRejects_2
dumpRejects_2: Inspector [off]
AttributeRenamer_11
    ATTR_TABLE = RENAME_SET_DEFAULT neigh.STANOX > STANOX
    MISSING_INPUT_ATTRS = REMOVE
    -> AttributeKeeper_29
AttributeKeeper_29
    CREATE_BULK_MODE_FEATURES = NO
    KEEP_ATTRS = CRS,Description,STANOX,TIPLOC,dataSource,fme_color,stop_lat,stop_lon,easting,northing
    -> Reprojector_LL_2
Reprojector_LL_2
    DEST = LL-WGS84
    INTERPOLATION_TYPE_NAME = Nearest Neighbor
    RASTER_CELL_SIZE = Preserve Cells
    RASTER_TOLERANCE = 0.0
    REPROJECTED -> Sorter_8
FeatureWriter_2
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = yes
    CSV2_QUALIFY_FIELD_VALUES = yes
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(outputPath)
    DATASET_ATTR = _dataset
    FEATURE_TYPE_LIST_ATTR = _feature_types
    FORMAT = CSV2
    TOTAL_FEATURES_WRITTEN_ATTR = _total_features_written
    SUMMARY -> inspectorOutputSummary
inspectorOutputSummary: Inspector
overallOutputStats: StatisticsCalculator
    CALCULATION_MODE = NUMERIC
    FEAT_STATS = TIPLOC,NUMERIC_MODE,,,COUNT,,,,,,,,,,
    GROUP_BY = dataSource
    SUMMARY -> overallOutputStats_2
overallOutputStats_2: Inspector
nullCrs: TestFilter
    DEFAULT_VALUE = <UNFILTERED>
    TEST_LIST = "BOOL_OP,OR,COMPOSITE_TEST,""""""1"""""",TEST_CLAUSE,TEST CRS ATTRIBUTE_HAS_A_VALUE """,notNull
    notNull -> countCRS
    notNull -> FeatureJoiner [RIGHT]
countCRS: StatisticsCalculator
    CALCULATION_MODE = NUMERIC
    FEAT_STATS = CRS,NUMERIC_MODE,,,COUNT,,,,,,,,,,
    GROUP_BY = CRS
    SUMMARY -> moreThanOne
moreThanOne: TestFilter
    DEFAULT_VALUE = <UNFILTERED>
    TEST_LIST = "BOOL_OP,OR,COMPOSITE_TEST,""""""1"""""",TEST_CLAUSE,NUM_TEST @Value(CRS.total_count) > 1",MoreThanOne
    MoreThanOne -> FeatureJoiner [LEFT]
FeatureJoiner
    ATTR_CONFLICT_RES = Use Left
    GEOMETRY_HANDLING = Use Left
    JOIN_KEYS = CRS CRS STRING
    JOIN_MODE = Inner
    JOINED -> Sorter
Sorter
    SORT_PARM = CRS ALPHA ASCENDING
    SORTED -> multiTiplocCrs
    SORTED -> FeatureWriter_3 [Output]
FeatureWriter_3
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = yes
    CSV2_QUALIFY_FIELD_VALUES = yes
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(outputPath)
    DATASET_ATTR = _dataset
    FEATURE_TYPE_LIST_ATTR = _feature_types
    FORMAT = CSV2
    TOTAL_FEATURES_WRITTEN_ATTR = _total_features_written
multiTiplocCrs: Inspector

Bookmark: removeDuplicateSTANOX
Sorter_8
    SORT_PARM = STANOX NUMERIC ASCENDING TIPLOC ALPHA ASCENDING
    SORTED -> duplicateStanox
duplicateStanox: DuplicateFilter
    INPUT_ORDERED_CHOICE = No
    KEYATTR = STANOX
    UNIQUE -> FeatureJoiner_31 [LEFT]
    DUPLICATE -> testNullTiploc
testNullTiploc: TestFilter
    DEFAULT_VALUE = <UNFILTERED>
    TEST_LIST = "BOOL_OP,OR,COMPOSITE_TEST,""""""1"""""",TEST_CLAUSE,TEST TIPLOC NOT_ATTRIBUTE_HAS_A_VALUE """,no value
    no value -> AttributeRenamer_9
    <UNFILTERED> -> AttributeRenamer_9
AttributeRenamer_9
    ATTR_TABLE:
      RENAME_SET_DEFAULT CRS > dup.CRS
      RENAME_SET_DEFAULT dataSource > dup.dataSource
      RENAME_SET_DEFAULT Description > dup.Description
      RENAME_SET_DEFAULT STANOX > dup.STANOX
      RENAME_SET_DEFAULT TIPLOC > dup.TIPLOC
      RENAME_SET_DEFAULT stop_lat > dup.stop_lat
      RENAME_SET_DEFAULT stop_lon > dup.stop_lon
      RENAME_SET_DEFAULT fme_color > dup.fme_color
      RENAME_SET_DEFAULT easting > dup.easting
      RENAME_SET_DEFAULT northing > dup.northing
    MISSING_INPUT_ATTRS = REMOVE
    -> FeatureJoiner_31 [RIGHT]
FeatureJoiner_31
    ATTR_CONFLICT_RES = Use Left
    GEOMETRY_HANDLING = Aggregate Left and Right (Enforce Unique Names)
    JOIN_KEYS = STANOX dup.STANOX NUM
    JOIN_MODE = Inner
    JOINED -> TestFilter
    UNJOINED_LEFT -> Junction_10
TestFilter
    DEFAULT_VALUE = <UNFILTERED>
    TEST_LIST:
      "BOOL_OP,AND,COMPOSITE_TEST,""""""1 AND 2 AND 3"""""",TEST_CLAUSE,CASE_INSENSITIVE_TEST TIPLOC ATTRIBUTE_HAS_A_VALUE ""
      CASE_INSENSITIVE_TEST dup.TIPLOC ATTRIBUTE_HAS_A_VALUE ""
      CASE_INSENSITIVE_TEST @Value(TIPLOC) != @Value(dup.TIPLOC)",different TIPLOC
    different TIPLOC -> AttributeKeeper_23
    different TIPLOC -> AttributeRenamer_10
    <UNFILTERED> -> sameName
sameName: TestFilter
    DEFAULT_VALUE = <UNFILTERED>
    TEST_LIST = "BOOL_OP,OR,COMPOSITE_TEST,""""""1"""""",TEST_CLAUSE,CASE_INSENSITIVE_TEST @Value(Description) = @Value(dup.Description)",sameName
    sameName -> AttributeCreator_2
    <UNFILTERED> -> VertexExtractor_9
VertexExtractor_9
    Point -> AttributeRemover_19
AttributeRemover_19
    REMOVE_ATTRS = _feature_number,_part_number,_vertex_number,_x,_y,_z
    -> LineBuilder_8
LineBuilder_8
    ACCUM_INPUT_ATTRS = Use Attributes From One Feature
    GROUP_BY = STANOX
    REMOVE_DUPLICATES = No
    POINT -> AttributeCreator_2
    LINE -> Reprojector_NG_4
    POLYGON -> Reprojector_NG_4
Reprojector_NG_4
    DEST = EPSG:27700
    INTERPOLATION_TYPE_NAME = Nearest Neighbor
    RASTER_CELL_SIZE = Preserve Cells
    RASTER_TOLERANCE = 0.0
    REPROJECTED -> LengthCalculator_8
LengthCalculator_8
    DIM = 2
    LEN_ATTR = _length
    MULT = 1
    -> testLength
testLength: TestFilter
    DEFAULT_VALUE = <UNFILTERED>
    TEST_LIST = "BOOL_OP,OR,COMPOSITE_TEST,""""""1"""""",TEST_CLAUSE,NUM_TEST @Value(_length) <= 100",less100m_apart
    less100m_apart -> AttributeCreator_2
    <UNFILTERED> -> AttributeRenamer_10
    <UNFILTERED> -> AttributeKeeper_23
AttributeCreator_2
    ATTR_TABLE:
      SET_TO STANOX = FME_CONDITIONAL:DEFAULT_VALUE'@Value(STANOX)'BOOL_OP;OR;COMPOSITE_TEST;1 OR 2 OR 3;CASE_SENSITIVE_TEST STANOX ATTRIBUTE_IS_EMPTY _FME_BLANK_STRING_;CASE_SENSITIVE_TEST STANOX ATTRIBUTE_VALUE_NULL _FME_BLANK_STRING_;CASE_SENSITIVE_TEST STANOX ATTRIBUTE_IS_MISSING _FME_BLANK_STRING_'@Value(dup.STANOX)'FME_NUM_CONDITIONS2___
      SET_TO TIPLOC = FME_CONDITIONAL:DEFAULT_VALUE'@Value(TIPLOC)'BOOL_OP;OR;COMPOSITE_TEST;1 OR 2 OR 3;CASE_SENSITIVE_TEST TIPLOC ATTRIBUTE_IS_EMPTY _FME_BLANK_STRING_;CASE_SENSITIVE_TEST TIPLOC ATTRIBUTE_VALUE_NULL _FME_BLANK_STRING_;CASE_SENSITIVE_TEST TIPLOC ATTRIBUTE_IS_MISSING _FME_BLANK_STRING_'@Value(dup.TIPLOC)'FME_NUM_CONDITIONS2___
      SET_TO Description = FME_CONDITIONAL:DEFAULT_VALUE'@Value(Description)'BOOL_OP;OR;COMPOSITE_TEST;1 OR 2 OR 3;CASE_SENSITIVE_TEST Description ATTRIBUTE_IS_EMPTY _FME_BLANK_STRING_;CASE_SENSITIVE_TEST Description ATTRIBUTE_VALUE_NULL _FME_BLANK_STRING_;CASE_SENSITIVE_TEST Description ATTRIBUTE_IS_MISSING _FME_BLANK_STRING_'@Value(dup.Description)'FME_NUM_CONDITIONS2___
      SET_TO CRS = FME_CONDITIONAL:DEFAULT_VALUE'@Value(CRS)'BOOL_OP;OR;COMPOSITE_TEST;1 OR 2 OR 3;CASE_SENSITIVE_TEST CRS ATTRIBUTE_IS_EMPTY _FME_BLANK_STRING_;CASE_SENSITIVE_TEST CRS ATTRIBUTE_VALUE_NULL _FME_BLANK_STRING_;CASE_SENSITIVE_TEST CRS ATTRIBUTE_IS_MISSING _FME_BLANK_STRING_'@Value(dup.CRS)'FME_NUM_CONDITIONS2___
      SET_TO stop_lat = FME_CONDITIONAL:DEFAULT_VALUE'@Value(stop_lat)'BOOL_OP;OR;COMPOSITE_TEST;1 OR 2 OR 3;CASE_SENSITIVE_TEST stop_lat ATTRIBUTE_IS_EMPTY _FME_BLANK_STRING_;CASE_SENSITIVE_TEST stop_lat ATTRIBUTE_VALUE_NULL _FME_BLANK_STRING_;CASE_SENSITIVE_TEST stop_lat ATTRIBUTE_IS_MISSING _FME_BLANK_STRING_'@Value(dup.stop_lat)'FME_NUM_CONDITIONS2___
      SET_TO stop_lon = FME_CONDITIONAL:DEFAULT_VALUE'@Value(stop_lon)'BOOL_OP;OR;COMPOSITE_TEST;1 OR 2 OR 3;CASE_SENSITIVE_TEST stop_lon ATTRIBUTE_IS_EMPTY _FME_BLANK_STRING_;CASE_SENSITIVE_TEST stop_lon ATTRIBUTE_VALUE_NULL _FME_BLANK_STRING_;CASE_SENSITIVE_TEST stop_lon ATTRIBUTE_IS_MISSING _FME_BLANK_STRING_'@Value(dup.stop_lon)'FME_NUM_CONDITIONS2___
      SET_TO easting = FME_CONDITIONAL:DEFAULT_VALUE'@Value(easting)'BOOL_OP;OR;COMPOSITE_TEST;1 OR 2 OR 3;CASE_SENSITIVE_TEST easting ATTRIBUTE_IS_EMPTY _FME_BLANK_STRING_;CASE_SENSITIVE_TEST easting ATTRIBUTE_VALUE_NULL _FME_BLANK_STRING_;CASE_SENSITIVE_TEST easting ATTRIBUTE_IS_MISSING _FME_BLANK_STRING_'@Value(dup.easting)'FME_NUM_CONDITIONS2___
      SET_TO northing = FME_CONDITIONAL:DEFAULT_VALUE'@Value(northing)'BOOL_OP;OR;COMPOSITE_TEST;1 OR 2 OR 3;CASE_SENSITIVE_TEST northing ATTRIBUTE_IS_EMPTY _FME_BLANK_STRING_;CASE_SENSITIVE_TEST northing ATTRIBUTE_VALUE_NULL _FME_BLANK_STRING_;CASE_SENSITIVE_TEST northing ATTRIBUTE_IS_MISSING _FME_BLANK_STRING_'@Value(dup.northing)'FME_NUM_CONDITIONS2___
    -> AttributeKeeper_23
AttributeRenamer_10
    ATTR_TABLE:
      RENAME_SET_DEFAULT dup.CRS > CRS
      RENAME_SET_DEFAULT dup.dataSource > dataSource
      RENAME_SET_DEFAULT dup.Description > Description
      RENAME_SET_DEFAULT dup.STANOX > STANOX
      RENAME_SET_DEFAULT dup.TIPLOC > TIPLOC
      RENAME_SET_DEFAULT dup.stop_lat > stop_lat
      RENAME_SET_DEFAULT dup.stop_lon > stop_lon
      RENAME_SET_DEFAULT dup.fme_color > fme_color
      RENAME_SET_DEFAULT dup.easting > easting
      RENAME_SET_DEFAULT dup.northing > northing
    MISSING_INPUT_ATTRS = REMOVE
    -> AttributeKeeper_23
AttributeKeeper_23
    CREATE_BULK_MODE_FEATURES = NO
    KEEP_ATTRS = CRS,Description,STANOX,TIPLOC,dataSource,stop_lat,stop_lon,easting,northing
    -> Junction_10
Junction_10
    -> FeatureWriter_2 [Output]
    -> AttributeCreator_15
